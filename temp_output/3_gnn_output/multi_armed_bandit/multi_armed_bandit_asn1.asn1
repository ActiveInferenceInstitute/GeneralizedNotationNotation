MultiArmedBanditAgent-Schema DEFINITIONS AUTOMATIC TAGS ::= BEGIN

-- GNN Model Schema Definition
-- Model: Multi Armed Bandit Agent
-- This model describes a 3-armed bandit as a degenerate POMDP:
-- 
-- - 3 hidden states representing the "reward context" (which arm is currently best).
-- - 3 observations representing reward signals (no-reward, small-reward, big-reward).
-- - 3 actions: pull arm 0, pull arm 1, or pull arm 2.
-- - Context switches slowly (sticky transitions), testing exploration vs exploitation.
-- - The agent prefers big-reward observations (observation 2).
-- - Tests the bandit structure: meaningful actions despite nearly-static state dynamics.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Multi Armed Bandit Agent",
    version "1.0",
    annotation "This model describes a 3-armed bandit as a degenerate POMDP:  - 3 hidden states representing the ""reward context"" (which arm is currently best). - 3 observations representing reward signals (no-reward, small-reward, big-reward). - 3 actions: pull arm 0, pull arm 1, or pull arm 2. - Context switches slowly (sticky transitions), testing exploration vs exploitation. - The agent prefers big-reward observations (observation 2). - Tests the bandit structure: meaningful actions despite nearly-static state dynamics.",
    variables {
        {
            name "A",
            varType "likelihood_matrix",
            dataType "float"
            dimensions { 3, 3 }
        },
        {
            name "B",
            varType "transition_matrix",
            dataType "float"
            dimensions { 3, 3, 3 }
        },
        {
            name "C",
            varType "preference_vector",
            dataType "float"
            dimensions { 3 }
        }
    }
}

END -- MultiArmedBanditAgent-Schema


-- MODEL_DATA: {"model_name":"Multi Armed Bandit Agent","version":"1.0","annotation":"This model describes a 3-armed bandit as a degenerate POMDP:\n\n- 3 hidden states representing the \"reward context\" (which arm is currently best).\n- 3 observations representing reward signals (no-reward, small-reward, big-reward).\n- 3 actions: pull arm 0, pull arm 1, or pull arm 2.\n- Context switches slowly (sticky transitions), testing exploration vs exploitation.\n- The agent prefers big-reward observations (observation 2).\n- Tests the bandit structure: meaningful actions despite nearly-static state dynamics.","variables":[{"name":"A","var_type":"likelihood_matrix","data_type":"float","dimensions":[3,3],"description":"Reward likelihood given context state"},{"name":"B","var_type":"transition_matrix","data_type":"float","dimensions":[3,3,3],"description":"Context transitions (mostly identity \u2014 context is sticky)"},{"name":"C","var_type":"preference_vector","data_type":"float","dimensions":[3],"description":"Prefer big rewards"},{"name":"D","var_type":"prior_vector","data_type":"float","dimensions":[3],"description":"Prior over reward context"},{"name":"s","var_type":"hidden_state","data_type":"float","dimensions":[3,1],"description":"Current reward context belief"},{"name":"s_prime","var_type":"hidden_state","data_type":"float","dimensions":[3,1],"description":"Next context belief"},{"name":"o","var_type":"observation","data_type":"integer","dimensions":[3,1],"description":"Reward observation"},{"name":"\u03c0","var_type":"policy","data_type":"float","dimensions":[3],"description":"Policy over arms"},{"name":"u","var_type":"action","data_type":"integer","dimensions":[1],"description":"Arm pulled"},{"name":"G","var_type":"policy","data_type":"float","dimensions":[1],"description":"Expected Free Energy"},{"name":"t","var_type":"hidden_state","data_type":"integer","dimensions":[1],"description":"Discrete time step"}],"connections":[{"source_variables":["D"],"target_variables":["s"],"connection_type":"directed","weight":null,"description":null},{"source_variables":["s"],"target_variables":["A"],"connection_type":"undirected","weight":null,"description":null},{"source_variables":["A"],"target_variables":["o"],"connection_type":"undirected","weight":null,"description":null},{"source_variables":["s"],"target_variables":["s_prime"],"connection_type":"directed","weight":null,"description":null},{"source_variables":["s"],"target_variables":["B"],"connection_type":"undirected","weight":null,"description":null},{"source_variables":["C"],"target_variables":["G"],"connection_type":"directed","weight":null,"description":null},{"source_variables":["G"],"target_variables":["\u03c0"],"connection_type":"directed","weight":null,"description":null},{"source_variables":["\u03c0"],"target_variables":["u"],"connection_type":"directed","weight":null,"description":null},{"source_variables":["B"],"target_variables":["u"],"connection_type":"directed","weight":null,"description":null},{"source_variables":["u"],"target_variables":["s_prime"],"connection_type":"directed","weight":null,"description":null}],"parameters":[{"name":"A","value":[[0.1,0.5,0.5],[0.3,0.4,0.3],[0.6,0.1,0.2]],"type_hint":null,"description":null},{"name":"B","value":[[[0.9,0.05,0.05],[0.05,0.9,0.05],[0.05,0.05,0.9]],[[0.9,0.05,0.05],[0.05,0.9,0.05],[0.05,0.05,0.9]],[[0.9,0.05,0.05],[0.05,0.9,0.05],[0.05,0.05,0.9]]],"type_hint":null,"description":null},{"name":"C","value":[[0.0,1.0,3.0]],"type_hint":null,"description":null},{"name":"D","value":[[0.33333,0.33333,0.33333]],"type_hint":null,"description":null}],"equations":[],"time_specification":{"time_type":"Dynamic","discretization":null,"horizon":"Unbounded","step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"t","ontology_term":"Time","description":null}]}
