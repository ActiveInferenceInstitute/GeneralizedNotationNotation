Multi-AgentCooperativeActiveInference-Schema DEFINITIONS AUTOMATIC TAGS ::= BEGIN

-- GNN Model Schema Definition
-- Model: Multi-Agent Cooperative Active Inference
-- Two Active Inference agents cooperating on a joint task:
-- 
-- - Agent 1 and Agent 2 each maintain independent beliefs
-- - Shared observation space: agents observe each other's actions
-- - Joint task state includes both agents' positions (4x4 = 16 joint states)
-- - Cooperative preferences: both agents prefer the same goal configuration
-- - Models social cognition and coordination without explicit communication

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Multi-Agent Cooperative Active Inference",
    version "1.0",
    annotation "Two Active Inference agents cooperating on a joint task:  - Agent 1 and Agent 2 each maintain independent beliefs - Shared observation space: agents observe each other's actions - Joint task state includes both agents' positions (4x4 = 16 joint states) - Cooperative preferences: both agents prefer the same goal configuration - Models social cognition and coordination without explicit communication",
    variables {
        {
            name "A1",
            varType "action",
            dataType "float"
            dimensions { 4, 4 }
        },
        {
            name "B1",
            varType "hidden_state",
            dataType "float"
            dimensions { 4, 4, 3 }
        },
        {
            name "C1",
            varType "hidden_state",
            dataType "float"
            dimensions { 4 }
        }
    }
}

END -- Multi-AgentCooperativeActiveInference-Schema


-- MODEL_DATA: {"model_name":"Multi-Agent Cooperative Active Inference","version":"1.0","annotation":"Two Active Inference agents cooperating on a joint task:\n\n- Agent 1 and Agent 2 each maintain independent beliefs\n- Shared observation space: agents observe each other's actions\n- Joint task state includes both agents' positions (4x4 = 16 joint states)\n- Cooperative preferences: both agents prefer the same goal configuration\n- Models social cognition and coordination without explicit communication","variables":[{"name":"A1","var_type":"action","data_type":"float","dimensions":[4,4],"description":"Agent 1 likelihood"},{"name":"B1","var_type":"hidden_state","data_type":"float","dimensions":[4,4,3],"description":"Agent 1 transitions (3 actions)"},{"name":"C1","var_type":"hidden_state","data_type":"float","dimensions":[4],"description":"Agent 1 preferences"},{"name":"D1","var_type":"hidden_state","data_type":"float","dimensions":[4],"description":"Agent 1 prior"},{"name":"s1","var_type":"hidden_state","data_type":"float","dimensions":[4,1],"description":"Agent 1 hidden state"},{"name":"s1_prime","var_type":"hidden_state","data_type":"float","dimensions":[4,1],"description":"Agent 1 next hidden state"},{"name":"o1","var_type":"observation","data_type":"integer","dimensions":[4,1],"description":"Agent 1 observations (includes Agent 2 obs)"},{"name":"\u03c01","var_type":"hidden_state","data_type":"float","dimensions":[3],"description":"Agent 1 policy"},{"name":"u1","var_type":"action","data_type":"integer","dimensions":[1],"description":"Agent 1 action"},{"name":"G1","var_type":"hidden_state","data_type":"float","dimensions":[1],"description":"Agent 1 EFE"},{"name":"A2","var_type":"action","data_type":"float","dimensions":[4,4],"description":"Agent 2 likelihood"},{"name":"B2","var_type":"hidden_state","data_type":"float","dimensions":[4,4,3],"description":"Agent 2 transitions (3 actions)"},{"name":"C2","var_type":"hidden_state","data_type":"float","dimensions":[4],"description":"Agent 2 preferences"},{"name":"D2","var_type":"hidden_state","data_type":"float","dimensions":[4],"description":"Agent 2 prior"},{"name":"s2","var_type":"hidden_state","data_type":"float","dimensions":[4,1],"description":"Agent 2 hidden state"},{"name":"s2_prime","var_type":"hidden_state","data_type":"float","dimensions":[4,1],"description":"Agent 2 next hidden state"},{"name":"o2","var_type":"observation","data_type":"integer","dimensions":[4,1],"description":"Agent 2 observations (includes Agent 1 obs)"},{"name":"\u03c02","var_type":"hidden_state","data_type":"float","dimensions":[3],"description":"Agent 2 policy"},{"name":"u2","var_type":"action","data_type":"integer","dimensions":[1],"description":"Agent 2 action"},{"name":"G2","var_type":"hidden_state","data_type":"float","dimensions":[1],"description":"Agent 2 EFE"},{"name":"s_joint","var_type":"hidden_state","data_type":"float","dimensions":[16,1],"description":"Joint state (Agent1_pos x Agent2_pos)"},{"name":"o_joint","var_type":"observation","data_type":"integer","dimensions":[4,1],"description":"Joint observation (goal achievement)"},{"name":"t","var_type":"hidden_state","data_type":"integer","dimensions":[1],"description":null}],"connections":[{"source_variables":["D1"],"target_variables":["s1"],"connection_type":"directed","weight":null,"description":null},{"source_variables":["s1"],"target_variables":["A1"],"connection_type":"undirected","weight":null,"description":null},{"source_variables":["A1"],"target_variables":["o1"],"connection_type":"undirected","weight":null,"description":null},{"source_variables":["s1"],"target_variables":["s1_prime"],"connection_type":"directed","weight":null,"description":null},{"source_variables":["C1"],"target_variables":["G1"],"connection_type":"directed","weight":null,"description":null},{"source_variables":["G1"],"target_variables":["\u03c01"],"connection_type":"directed","weight":null,"description":null},{"source_variables":["\u03c01"],"target_variables":["u1"],"connection_type":"directed","weight":null,"description":null},{"source_variables":["B1"],"target_variables":["u1"],"connection_type":"directed","weight":null,"description":null},{"source_variables":["D2"],"target_variables":["s2"],"connection_type":"directed","weight":null,"description":null},{"source_variables":["s2"],"target_variables":["A2"],"connection_type":"undirected","weight":null,"description":null},{"source_variables":["A2"],"target_variables":["o2"],"connection_type":"undirected","weight":null,"description":null},{"source_variables":["s2"],"target_variables":["s2_prime"],"connection_type":"directed","weight":null,"description":null},{"source_variables":["C2"],"target_variables":["G2"],"connection_type":"directed","weight":null,"description":null},{"source_variables":["G2"],"target_variables":["\u03c02"],"connection_type":"directed","weight":null,"description":null},{"source_variables":["\u03c02"],"target_variables":["u2"],"connection_type":"directed","weight":null,"description":null},{"source_variables":["B2"],"target_variables":["u2"],"connection_type":"directed","weight":null,"description":null},{"source_variables":["u1"],"target_variables":["s_joint"],"connection_type":"directed","weight":null,"description":null},{"source_variables":["u2"],"target_variables":["s_joint"],"connection_type":"directed","weight":null,"description":null},{"source_variables":["s_joint"],"target_variables":["o_joint"],"connection_type":"undirected","weight":null,"description":null},{"source_variables":["o1"],"target_variables":["s_joint"],"connection_type":"undirected","weight":null,"description":null},{"source_variables":["o2"],"target_variables":["s_joint"],"connection_type":"undirected","weight":null,"description":null}],"parameters":[{"name":"A1","value":[[0.85,0.05,0.05,0.05],[0.05,0.85,0.05,0.05],[0.05,0.05,0.85,0.05],[0.05,0.05,0.05,0.85]],"type_hint":null,"description":null},{"name":"A2","value":[[0.85,0.05,0.05,0.05],[0.05,0.85,0.05,0.05],[0.05,0.05,0.85,0.05],[0.05,0.05,0.05,0.85]],"type_hint":null,"description":null},{"name":"C1","value":[[-1.0,-1.0,-1.0,2.0]],"type_hint":null,"description":null},{"name":"C2","value":[[-1.0,-1.0,-1.0,2.0]],"type_hint":null,"description":null},{"name":"D1","value":[[0.25,0.25,0.25,0.25]],"type_hint":null,"description":null},{"name":"D2","value":[[0.25,0.25,0.25,0.25]],"type_hint":null,"description":null},{"name":"B1","value":[[[0.9,0.1,0.0,0.0],[0.0,0.9,0.1,0.0],[0.0,0.0,0.9,0.1],[0.1,0.0,0.0,0.9]],[[0.9,0.0,0.0,0.1],[0.1,0.9,0.0,0.0],[0.0,0.1,0.9,0.0],[0.0,0.0,0.1,0.9]],[[0.8,0.1,0.1,0.0],[0.1,0.8,0.0,0.1],[0.1,0.0,0.8,0.1],[0.0,0.1,0.1,0.8]]],"type_hint":null,"description":null},{"name":"B2","value":[[[0.9,0.1,0.0,0.0],[0.0,0.9,0.1,0.0],[0.0,0.0,0.9,0.1],[0.1,0.0,0.0,0.9]],[[0.9,0.0,0.0,0.1],[0.1,0.9,0.0,0.0],[0.0,0.1,0.9,0.0],[0.0,0.0,0.1,0.9]],[[0.8,0.1,0.1,0.0],[0.1,0.8,0.0,0.1],[0.1,0.0,0.8,0.1],[0.0,0.1,0.1,0.8]]],"type_hint":null,"description":null}],"equations":[],"time_specification":{"time_type":"Dynamic","discretization":null,"horizon":20,"step_size":null},"ontology_mappings":[{"variable_name":"A1","ontology_term":"LikelihoodMatrix","description":null},{"variable_name":"B1","ontology_term":"TransitionMatrix","description":null},{"variable_name":"C1","ontology_term":"LogPreferenceVector","description":null},{"variable_name":"D1","ontology_term":"PriorOverHiddenStates","description":null},{"variable_name":"s1","ontology_term":"Agent1HiddenState","description":null},{"variable_name":"s1_prime","ontology_term":"Agent1NextHiddenState","description":null},{"variable_name":"o1","ontology_term":"Agent1Observation","description":null},{"variable_name":"\u03c01","ontology_term":"Agent1PolicyVector","description":null},{"variable_name":"u1","ontology_term":"Agent1Action","description":null},{"variable_name":"G1","ontology_term":"Agent1ExpectedFreeEnergy","description":null},{"variable_name":"A2","ontology_term":"LikelihoodMatrix","description":null},{"variable_name":"B2","ontology_term":"TransitionMatrix","description":null},{"variable_name":"C2","ontology_term":"LogPreferenceVector","description":null},{"variable_name":"D2","ontology_term":"PriorOverHiddenStates","description":null},{"variable_name":"s2","ontology_term":"Agent2HiddenState","description":null},{"variable_name":"s2_prime","ontology_term":"Agent2NextHiddenState","description":null},{"variable_name":"o2","ontology_term":"Agent2Observation","description":null},{"variable_name":"\u03c02","ontology_term":"Agent2PolicyVector","description":null},{"variable_name":"u2","ontology_term":"Agent2Action","description":null},{"variable_name":"G2","ontology_term":"Agent2ExpectedFreeEnergy","description":null},{"variable_name":"s_joint","ontology_term":"JointState","description":null},{"variable_name":"o_joint","ontology_term":"JointObservation","description":null},{"variable_name":"t","ontology_term":"Time","description":null}]}
