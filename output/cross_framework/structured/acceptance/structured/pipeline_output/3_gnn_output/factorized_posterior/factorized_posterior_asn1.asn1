FactorizedPosteriorAgent-Schema DEFINITIONS AUTOMATIC TAGS ::= BEGIN

-- GNN Model Schema Definition
-- Model: Factorized Posterior Agent
-- A mean-field factorized POMDP agent. The joint posterior over two
-- independent state factors `s_1` (location) and `s_2` (goal identity) is
-- approximated as the product of marginals Q(s_1, s_2) = Q(s_1) * Q(s_2).
-- This is the canonical simplification used in variational inference when
-- exact joint posteriors are computationally intractable.
-- 
-- - Two state factors: location (4 states), goal (2 states)
-- - Two observation modalities: visual (3 obs), proprioceptive (2 obs)
-- - Separate transition matrices B_1 (location × action) and B_2 (goal is static)
-- - Explicit factorization declared in ## Equations
-- - Tests multi-factor / multi-modality handling in the parser

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Factorized Posterior Agent",
    version "1.0",
    annotation "A mean-field factorized POMDP agent. The joint posterior over two independent state factors `s_1` (location) and `s_2` (goal identity) is approximated as the product of marginals Q(s_1, s_2) = Q(s_1) * Q(s_2). This is the canonical simplification used in variational inference when exact joint posteriors are computationally intractable.  - Two state factors: location (4 states), goal (2 states) - Two observation modalities: visual (3 obs), proprioceptive (2 obs) - Separate transition matrices B_1 (location × action) and B_2 (goal is static) - Explicit factorization declared in ## Equations - Tests multi-factor / multi-modality handling in the parser",
    variables {
        {
            name "s_f0",
            varType "hidden_state",
            dataType "float"
            dimensions { 4, 1 }
        },
        {
            name "s_f1",
            varType "hidden_state",
            dataType "float"
            dimensions { 2, 1 }
        },
        {
            name "o_m0",
            varType "observation",
            dataType "integer"
            dimensions { 3, 1 }
        }
    }
}

END -- FactorizedPosteriorAgent-Schema


-- MODEL_DATA: {"model_name":"Factorized Posterior Agent","version":"1.0","annotation":"A mean-field factorized POMDP agent. The joint posterior over two\nindependent state factors `s_1` (location) and `s_2` (goal identity) is\napproximated as the product of marginals Q(s_1, s_2) = Q(s_1) * Q(s_2).\nThis is the canonical simplification used in variational inference when\nexact joint posteriors are computationally intractable.\n\n- Two state factors: location (4 states), goal (2 states)\n- Two observation modalities: visual (3 obs), proprioceptive (2 obs)\n- Separate transition matrices B_1 (location \u00d7 action) and B_2 (goal is static)\n- Explicit factorization declared in ## Equations\n- Tests multi-factor / multi-modality handling in the parser","variables":[{"name":"s_f0","var_type":"hidden_state","data_type":"float","dimensions":[4,1],"description":"Factor 0: agent location (4 possible positions)"},{"name":"s_f1","var_type":"hidden_state","data_type":"float","dimensions":[2,1],"description":"Factor 1: goal identity (2 possible goals)"},{"name":"o_m0","var_type":"observation","data_type":"integer","dimensions":[3,1],"description":"Modality 0: visual observation (3 visual cues)"},{"name":"o_m1","var_type":"observation","data_type":"integer","dimensions":[2,1],"description":"Modality 1: proprioceptive observation (2 body states)"},{"name":"u","var_type":"action","data_type":"integer","dimensions":[3,1],"description":"3 possible actions: stay, forward, backward"},{"name":"A_m0","var_type":"action","data_type":"float","dimensions":[3,4,2],"description":"Visual likelihood: depends on both factors"},{"name":"A_m1","var_type":"action","data_type":"float","dimensions":[2,4],"description":"Proprioceptive likelihood: depends only on location"},{"name":"B_f0","var_type":"hidden_state","data_type":"float","dimensions":[4,4,3],"description":"Location transitions (depends on action)"},{"name":"B_f1","var_type":"hidden_state","data_type":"float","dimensions":[2,2],"description":"Goal transitions (typically identity \u2014 goal is static)"},{"name":"D_f0","var_type":"hidden_state","data_type":"float","dimensions":[4,1],"description":"Prior over locations (uniform)"},{"name":"D_f1","var_type":"hidden_state","data_type":"float","dimensions":[2,1],"description":"Prior over goals"},{"name":"C_m0","var_type":"hidden_state","data_type":"float","dimensions":[3,1],"description":"Visual preferences"},{"name":"C_m1","var_type":"hidden_state","data_type":"float","dimensions":[2,1],"description":"Proprioceptive preferences"}],"connections":[{"annotation":null,"source_variables":["D_f0"],"target_variables":["s_f0"],"connection_type":"directed","weight":null,"description":null},{"annotation":null,"source_variables":["D_f1"],"target_variables":["s_f1"],"connection_type":"directed","weight":null,"description":null},{"annotation":null,"source_variables":["s_f0","u"],"target_variables":["B_f0"],"connection_type":"directed","weight":null,"description":null},{"annotation":null,"source_variables":["B_f0"],"target_variables":["s_f0"],"connection_type":"directed","weight":null,"description":null},{"annotation":null,"source_variables":["s_f1"],"target_variables":["B_f1"],"connection_type":"directed","weight":null,"description":null},{"annotation":null,"source_variables":["B_f1"],"target_variables":["s_f1"],"connection_type":"directed","weight":null,"description":null},{"annotation":null,"source_variables":["s_f0","s_f1"],"target_variables":["A_m0"],"connection_type":"directed","weight":null,"description":null},{"annotation":null,"source_variables":["A_m0"],"target_variables":["o_m0"],"connection_type":"directed","weight":null,"description":null},{"annotation":null,"source_variables":["s_f0"],"target_variables":["A_m1"],"connection_type":"directed","weight":null,"description":null},{"annotation":null,"source_variables":["A_m1"],"target_variables":["o_m1"],"connection_type":"directed","weight":null,"description":null},{"annotation":null,"source_variables":["C_m0"],"target_variables":["o_m0"],"connection_type":"undirected","weight":null,"description":null},{"annotation":null,"source_variables":["C_m1"],"target_variables":["o_m1"],"connection_type":"undirected","weight":null,"description":null}],"parameters":[{"name":"A_m0","value":[[[0.7,0.1],[0.1,0.7],[0.1,0.1],[0.1,0.1]],[[0.1,0.7],[0.7,0.1],[0.1,0.1],[0.1,0.1]],[[0.2,0.2],[0.2,0.2],[0.8,0.8],[0.8,0.8]]],"type_hint":null,"description":null},{"name":"A_m1","value":[[0.9,0.1,0.1,0.1],[0.1,0.9,0.9,0.9]],"type_hint":null,"description":null},{"name":"D_f0","value":[[0.25,0.25,0.25,0.25]],"type_hint":null,"description":null},{"name":"D_f1","value":[[0.6,0.4]],"type_hint":null,"description":null},{"name":"C_m0","value":[[0.0,0.0,1.0]],"type_hint":null,"description":null},{"name":"C_m1","value":[[0.5,0.5]],"type_hint":null,"description":null},{"name":"B_f0","value":[[[0.9,0.1,0.0,0.0],[0.1,0.9,0.0,0.0],[0.0,0.0,0.9,0.1],[0.0,0.0,0.1,0.9]],[[0.1,0.9,0.0,0.0],[0.0,0.1,0.9,0.0],[0.0,0.0,0.1,0.9],[0.9,0.0,0.0,0.1]],[[0.9,0.0,0.0,0.1],[0.1,0.9,0.0,0.0],[0.0,0.1,0.9,0.0],[0.0,0.0,0.1,0.9]]],"type_hint":null,"description":null},{"name":"B_f1","value":[[[1.0,0.0],[0.0,1.0]]],"type_hint":null,"description":null},{"name":"num_hidden_states","value":8,"type_hint":null,"description":null},{"name":"num_obs","value":6,"type_hint":null,"description":null},{"name":"num_hidden_states_factor0","value":4,"type_hint":null,"description":null},{"name":"num_hidden_states_factor1","value":2,"type_hint":null,"description":null},{"name":"num_obs_modality0","value":3,"type_hint":null,"description":null},{"name":"num_obs_modality1","value":2,"type_hint":null,"description":null},{"name":"num_actions","value":3,"type_hint":null,"description":null},{"name":"num_factors","value":2,"type_hint":null,"description":null},{"name":"num_modalities","value":2,"type_hint":null,"description":null},{"name":"num_timesteps","value":15,"type_hint":null,"description":null}],"equations":[],"time_specification":{"time_type":"Dynamic","discretization":"DiscreteTime","horizon":15,"step_size":null},"ontology_mappings":[{"variable_name":"s_f0","ontology_term":"HiddenStateFactor0","description":null},{"variable_name":"s_f1","ontology_term":"HiddenStateFactor1","description":null},{"variable_name":"o_m0","ontology_term":"ObservationModality0","description":null},{"variable_name":"o_m1","ontology_term":"ObservationModality1","description":null},{"variable_name":"u","ontology_term":"Action","description":null},{"variable_name":"A_m0","ontology_term":"LikelihoodMatrixModality0","description":null},{"variable_name":"A_m1","ontology_term":"LikelihoodMatrixModality1","description":null},{"variable_name":"D_f0","ontology_term":"PriorFactor0","description":null},{"variable_name":"D_f1","ontology_term":"PriorFactor1","description":null},{"variable_name":"C_m0","ontology_term":"PreferenceModality0","description":null},{"variable_name":"C_m1","ontology_term":"PreferenceModality1","description":null}]}
