Curiosity-DrivenActiveInferenceAgent-Schema DEFINITIONS AUTOMATIC TAGS ::= BEGIN

-- GNN Model Schema Definition
-- Model: Curiosity-Driven Active Inference Agent
-- An Active Inference agent with:
-- - Explicit epistemic value (information gain / Bayesian surprise) component in G
-- - Separate instrumental value (preference satisfaction) component
-- - Precision parameter γ weighting epistemic vs instrumental contributions
-- - 5 hidden states, 5 observations, 4 actions in a navigation context
-- - Agent is rewarded for reducing posterior uncertainty

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Curiosity-Driven Active Inference Agent",
    version "1.0",
    annotation "An Active Inference agent with: - Explicit epistemic value (information gain / Bayesian surprise) component in G - Separate instrumental value (preference satisfaction) component - Precision parameter γ weighting epistemic vs instrumental contributions - 5 hidden states, 5 observations, 4 actions in a navigation context - Agent is rewarded for reducing posterior uncertainty",
    variables {
        {
            name "A",
            varType "likelihood_matrix",
            dataType "float"
            dimensions { 5, 5 }
        },
        {
            name "B",
            varType "transition_matrix",
            dataType "float"
            dimensions { 5, 5, 4 }
        },
        {
            name "C",
            varType "preference_vector",
            dataType "float"
            dimensions { 5 }
        }
    }
}

END -- Curiosity-DrivenActiveInferenceAgent-Schema


-- MODEL_DATA: {"model_name":"Curiosity-Driven Active Inference Agent","version":"1.0","annotation":"An Active Inference agent with:\n- Explicit epistemic value (information gain / Bayesian surprise) component in G\n- Separate instrumental value (preference satisfaction) component\n- Precision parameter \u03b3 weighting epistemic vs instrumental contributions\n- 5 hidden states, 5 observations, 4 actions in a navigation context\n- Agent is rewarded for reducing posterior uncertainty","variables":[{"name":"A","var_type":"likelihood_matrix","data_type":"float","dimensions":[5,5],"description":"Likelihood matrix"},{"name":"B","var_type":"transition_matrix","data_type":"float","dimensions":[5,5,4],"description":"Transition matrix (4 actions: up/down/left/right)"},{"name":"C","var_type":"preference_vector","data_type":"float","dimensions":[5],"description":"Instrumental preference vector (goal observations)"},{"name":"D","var_type":"prior_vector","data_type":"float","dimensions":[5],"description":"Prior over hidden states (uniform = no preference)"},{"name":"E","var_type":"policy","data_type":"float","dimensions":[4],"description":"Habit vector over actions"},{"name":"s","var_type":"hidden_state","data_type":"float","dimensions":[5,1],"description":"Hidden state belief"},{"name":"s_prime","var_type":"hidden_state","data_type":"float","dimensions":[5,1],"description":"Next hidden state belief"},{"name":"o","var_type":"observation","data_type":"integer","dimensions":[5,1],"description":"Current observation"},{"name":"\u03c0","var_type":"policy","data_type":"float","dimensions":[4],"description":"Policy distribution over actions"},{"name":"u","var_type":"action","data_type":"integer","dimensions":[1],"description":"Selected action"},{"name":"G","var_type":"policy","data_type":"float","dimensions":[1],"description":"Total Expected Free Energy (epistemic + instrumental)"},{"name":"G_epi","var_type":"policy","data_type":"float","dimensions":[1],"description":"Epistemic value component (information gain)"},{"name":"G_ins","var_type":"hidden_state","data_type":"float","dimensions":[1],"description":"Instrumental value component (preference satisfaction)"},{"name":"\u03b3","var_type":"hidden_state","data_type":"float","dimensions":[1],"description":"Precision weighting epistemic vs instrumental value"},{"name":"F","var_type":"hidden_state","data_type":"float","dimensions":[1],"description":"Variational Free Energy for state inference"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["s"],"target_variables":["s_prime"],"connection_type":"directed","weight":null,"description":null},{"annotation":null,"source_variables":["A"],"target_variables":["o"],"connection_type":"undirected","weight":null,"description":null},{"annotation":null,"source_variables":["C"],"target_variables":["G_ins"],"connection_type":"directed","weight":null,"description":null},{"annotation":null,"source_variables":["G_epi"],"target_variables":["G"],"connection_type":"directed","weight":null,"description":null},{"annotation":null,"source_variables":["G_ins"],"target_variables":["G"],"connection_type":"directed","weight":null,"description":null},{"annotation":null,"source_variables":["\u03b3"],"target_variables":["G"],"connection_type":"directed","weight":null,"description":null},{"annotation":null,"source_variables":["E"],"target_variables":["\u03c0"],"connection_type":"directed","weight":null,"description":null},{"annotation":null,"source_variables":["G"],"target_variables":["\u03c0"],"connection_type":"directed","weight":null,"description":null},{"annotation":null,"source_variables":["\u03c0"],"target_variables":["u"],"connection_type":"directed","weight":null,"description":null},{"annotation":null,"source_variables":["B"],"target_variables":["u"],"connection_type":"directed","weight":null,"description":null},{"annotation":null,"source_variables":["u"],"target_variables":["s_prime"],"connection_type":"directed","weight":null,"description":null},{"annotation":null,"source_variables":["s"],"target_variables":["F"],"connection_type":"undirected","weight":null,"description":null},{"annotation":null,"source_variables":["o"],"target_variables":["F"],"connection_type":"undirected","weight":null,"description":null}],"parameters":[{"name":"A","value":[[0.9,0.025,0.025,0.025,0.025],[0.025,0.9,0.025,0.025,0.025],[0.025,0.025,0.9,0.025,0.025],[0.025,0.025,0.025,0.9,0.025],[0.025,0.025,0.025,0.025,0.9]],"type_hint":null,"description":null},{"name":"B","value":[[[0.9,0.9,1.0,0.9],[0.1,0.0,0.1,0.0],[0.0,0.0,0.0,0.0],[0.0,0.0,0.0,0.0],[0.0,0.0,0.0,0.0]],[[0.1,0.1,0.0,0.0],[0.8,0.9,0.9,0.9],[0.1,0.0,0.1,0.0],[0.0,0.0,0.0,0.0],[0.0,0.0,0.0,0.0]],[[0.0,0.0,0.0,0.0],[0.1,0.1,0.0,0.0],[0.8,0.9,0.9,0.9],[0.1,0.0,0.1,0.0],[0.0,0.0,0.0,0.0]],[[0.0,0.0,0.0,0.0],[0.0,0.0,0.0,0.0],[0.1,0.1,0.0,0.0],[0.8,0.9,0.9,0.9],[0.1,0.0,0.1,0.0]],[[0.0,0.0,0.0,0.1],[0.0,0.0,0.0,0.1],[0.0,0.0,0.0,0.1],[0.1,0.1,0.0,0.1],[0.9,1.0,0.9,1.0]]],"type_hint":null,"description":null},{"name":"C","value":[[-2.0,-2.0,-2.0,-2.0,2.0]],"type_hint":null,"description":null},{"name":"D","value":[[0.2,0.2,0.2,0.2,0.2]],"type_hint":null,"description":null},{"name":"E","value":[[0.25,0.25,0.25,0.25]],"type_hint":null,"description":null},{"name":"\u03b3","value":[[1.0]],"type_hint":null,"description":null},{"name":"num_hidden_states","value":5,"type_hint":null,"description":null},{"name":"num_obs","value":5,"type_hint":null,"description":null},{"name":"num_actions","value":4,"type_hint":null,"description":null},{"name":"num_timesteps","value":30,"type_hint":null,"description":null},{"name":"epistemic_weight","value":1.0,"type_hint":null,"description":null},{"name":"instrumental_weight","value":1.0,"type_hint":null,"description":null}],"equations":[],"time_specification":{"time_type":"Dynamic","discretization":null,"horizon":30,"step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"E","ontology_term":"Habit","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"G","ontology_term":"ExpectedFreeEnergy","description":null},{"variable_name":"G_epi","ontology_term":"EpistemicValue","description":null},{"variable_name":"G_ins","ontology_term":"InstrumentalValue","description":null},{"variable_name":"\u03b3","ontology_term":"PrecisionParameter","description":null},{"variable_name":"F","ontology_term":"VariationalFreeEnergy","description":null},{"variable_name":"t","ontology_term":"Time","description":null}]}
