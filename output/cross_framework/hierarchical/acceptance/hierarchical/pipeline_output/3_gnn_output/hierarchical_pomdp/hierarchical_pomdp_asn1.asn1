HierarchicalActiveInferencePOMDP-Schema DEFINITIONS AUTOMATIC TAGS ::= BEGIN

-- GNN Model Schema Definition
-- Model: Hierarchical Active Inference POMDP
-- A two-level hierarchical POMDP where:
-- - Level 1 (fast): 4 observations, 4 hidden states, 3 actions
-- - Level 2 (slow): 2 contextual states that modulate Level 1 likelihood
-- - Higher-level beliefs are updated at a slower timescale
-- - Top-down predictions constrain bottom-up inference at Level 1

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Hierarchical Active Inference POMDP",
    version "1.0",
    annotation "A two-level hierarchical POMDP where: - Level 1 (fast): 4 observations, 4 hidden states, 3 actions - Level 2 (slow): 2 contextual states that modulate Level 1 likelihood - Higher-level beliefs are updated at a slower timescale - Top-down predictions constrain bottom-up inference at Level 1",
    variables {
        {
            name "A_level1",
            varType "action",
            dataType "float"
            dimensions { 4, 4 }
        },
        {
            name "B_level1",
            varType "hidden_state",
            dataType "float"
            dimensions { 4, 4, 3 }
        },
        {
            name "C_level1",
            varType "hidden_state",
            dataType "float"
            dimensions { 4 }
        }
    }
}

END -- HierarchicalActiveInferencePOMDP-Schema


-- MODEL_DATA: {"model_name":"Hierarchical Active Inference POMDP","version":"1.0","annotation":"A two-level hierarchical POMDP where:\n- Level 1 (fast): 4 observations, 4 hidden states, 3 actions\n- Level 2 (slow): 2 contextual states that modulate Level 1 likelihood\n- Higher-level beliefs are updated at a slower timescale\n- Top-down predictions constrain bottom-up inference at Level 1","variables":[{"name":"A_level1","var_type":"action","data_type":"float","dimensions":[4,4],"description":"Level 1 likelihood: observations x hidden states"},{"name":"B_level1","var_type":"hidden_state","data_type":"float","dimensions":[4,4,3],"description":"Level 1 transitions: next x prev x actions"},{"name":"C_level1","var_type":"hidden_state","data_type":"float","dimensions":[4],"description":"Level 1 preferences over observations"},{"name":"D_level1","var_type":"hidden_state","data_type":"float","dimensions":[4],"description":"Level 1 prior over hidden states"},{"name":"s_level1","var_type":"hidden_state","data_type":"float","dimensions":[4,1],"description":"Level 1 hidden state distribution"},{"name":"x_next1","var_type":"hidden_state","data_type":"float","dimensions":[4,1],"description":"Level 1 next hidden state"},{"name":"o_level1","var_type":"observation","data_type":"integer","dimensions":[4,1],"description":"Level 1 observations"},{"name":"\u03c01","var_type":"hidden_state","data_type":"float","dimensions":[3],"description":"Level 1 policy (actions)"},{"name":"u_level1","var_type":"action","data_type":"integer","dimensions":[1],"description":"Level 1 action"},{"name":"G1","var_type":"hidden_state","data_type":"float","dimensions":[1],"description":"Level 1 Expected Free Energy"},{"name":"A_level2","var_type":"action","data_type":"float","dimensions":[4,2],"description":"Level 2 likelihood: maps context to Level 1 hidden state prior"},{"name":"B_level2","var_type":"hidden_state","data_type":"float","dimensions":[2,2,1],"description":"Level 2 transitions (context switches)"},{"name":"C_level2","var_type":"hidden_state","data_type":"float","dimensions":[2],"description":"Level 2 preferences over context"},{"name":"D_level2","var_type":"hidden_state","data_type":"float","dimensions":[2],"description":"Level 2 prior over contextual states"},{"name":"s_level2","var_type":"hidden_state","data_type":"float","dimensions":[2,1],"description":"Level 2 contextual hidden state"},{"name":"o_level2","var_type":"observation","data_type":"float","dimensions":[4,1],"description":"Level 2 observation (= Level 1 hidden state distribution)"},{"name":"G2","var_type":"hidden_state","data_type":"float","dimensions":[1],"description":"Level 2 Expected Free Energy"},{"name":"t1","var_type":"hidden_state","data_type":"integer","dimensions":[1],"description":"Fast timescale counter"},{"name":"t2","var_type":"hidden_state","data_type":"integer","dimensions":[1],"description":"Slow timescale counter"}],"connections":[{"annotation":null,"source_variables":["D_level1"],"target_variables":["s_level1"],"connection_type":"directed","weight":null,"description":null},{"annotation":null,"source_variables":["s_level1"],"target_variables":["A_level1"],"connection_type":"undirected","weight":null,"description":null},{"annotation":null,"source_variables":["s_level1"],"target_variables":["x_next1"],"connection_type":"directed","weight":null,"description":null},{"annotation":null,"source_variables":["A_level1"],"target_variables":["o_level1"],"connection_type":"undirected","weight":null,"description":null},{"annotation":null,"source_variables":["C_level1"],"target_variables":["G1"],"connection_type":"directed","weight":null,"description":null},{"annotation":null,"source_variables":["G1"],"target_variables":["\u03c01"],"connection_type":"directed","weight":null,"description":null},{"annotation":null,"source_variables":["\u03c01"],"target_variables":["u_level1"],"connection_type":"directed","weight":null,"description":null},{"annotation":null,"source_variables":["B_level1"],"target_variables":["u_level1"],"connection_type":"directed","weight":null,"description":null},{"annotation":null,"source_variables":["u_level1"],"target_variables":["x_next1"],"connection_type":"directed","weight":null,"description":null},{"annotation":null,"source_variables":["s_level1"],"target_variables":["o_level2"],"connection_type":"directed","weight":null,"description":null},{"annotation":null,"source_variables":["D_level2"],"target_variables":["s_level2"],"connection_type":"directed","weight":null,"description":null},{"annotation":null,"source_variables":["s_level2"],"target_variables":["A_level2"],"connection_type":"undirected","weight":null,"description":null},{"annotation":null,"source_variables":["A_level2"],"target_variables":["D_level1"],"connection_type":"directed","weight":null,"description":null},{"annotation":null,"source_variables":["s_level2"],"target_variables":["B_level2"],"connection_type":"undirected","weight":null,"description":null},{"annotation":null,"source_variables":["C_level2"],"target_variables":["G2"],"connection_type":"directed","weight":null,"description":null},{"annotation":null,"source_variables":["G2"],"target_variables":["s_level2"],"connection_type":"directed","weight":null,"description":null}],"parameters":[{"name":"A_level1","value":[[0.85,0.05,0.05,0.05],[0.05,0.85,0.05,0.05],[0.05,0.05,0.85,0.05],[0.05,0.05,0.05,0.85]],"type_hint":null,"description":null},{"name":"B_level1","value":[[[1.0,0.0,0.0,0.0],[0.0,1.0,0.0,0.0],[0.0,0.0,1.0,0.0],[0.0,0.0,0.0,1.0]],[[0.0,1.0,0.0,0.0],[1.0,0.0,0.0,0.0],[0.0,0.0,0.0,1.0],[0.0,0.0,1.0,0.0]],[[0.0,0.0,1.0,0.0],[0.0,0.0,0.0,1.0],[1.0,0.0,0.0,0.0],[0.0,1.0,0.0,0.0]]],"type_hint":null,"description":null},{"name":"C_level1","value":[[0.1,0.1,0.1,1.0]],"type_hint":null,"description":null},{"name":"D_level1","value":[[0.25,0.25,0.25,0.25]],"type_hint":null,"description":null},{"name":"A_level2","value":[[0.9,0.1],[0.1,0.9],[0.5,0.5],[0.5,0.5]],"type_hint":null,"description":null},{"name":"B_level2","value":[[[0.9,0.1],[0.1,0.9]]],"type_hint":null,"description":null},{"name":"C_level2","value":[[0.0,0.5,0.0,0.5]],"type_hint":null,"description":null},{"name":"D_level2","value":[[0.5,0.5]],"type_hint":null,"description":null},{"name":"num_hidden_states","value":8,"type_hint":null,"description":null},{"name":"num_obs","value":16,"type_hint":null,"description":null},{"name":"num_actions","value":3,"type_hint":null,"description":null},{"name":"num_timesteps","value":20,"type_hint":null,"description":null},{"name":"num_hidden_states_l1","value":4,"type_hint":null,"description":null},{"name":"num_obs_l1","value":4,"type_hint":null,"description":null},{"name":"num_actions_l1","value":3,"type_hint":null,"description":null},{"name":"num_context_states_l2","value":2,"type_hint":null,"description":null},{"name":"timescale_ratio","value":5,"type_hint":null,"description":null}],"equations":[],"time_specification":{"time_type":"Dynamic","discretization":null,"horizon":"Unbounded","step_size":null},"ontology_mappings":[{"variable_name":"A_level1","ontology_term":"LikelihoodMatrix","description":null},{"variable_name":"B_level1","ontology_term":"TransitionMatrix","description":null},{"variable_name":"C_level1","ontology_term":"LogPreferenceVector","description":null},{"variable_name":"D_level1","ontology_term":"PriorOverHiddenStates","description":null},{"variable_name":"s_level1","ontology_term":"HiddenState","description":null},{"variable_name":"o_level1","ontology_term":"Observation","description":null},{"variable_name":"\u03c01","ontology_term":"PolicyVector","description":null},{"variable_name":"u_level1","ontology_term":"Action","description":null},{"variable_name":"G1","ontology_term":"ExpectedFreeEnergy","description":null},{"variable_name":"A_level2","ontology_term":"HigherLevelLikelihoodMatrix","description":null},{"variable_name":"B_level2","ontology_term":"ContextTransitionMatrix","description":null},{"variable_name":"s_level2","ontology_term":"ContextualHiddenState","description":null},{"variable_name":"o_level2","ontology_term":"HigherLevelObservation","description":null},{"variable_name":"G2","ontology_term":"HigherLevelExpectedFreeEnergy","description":null}]}
