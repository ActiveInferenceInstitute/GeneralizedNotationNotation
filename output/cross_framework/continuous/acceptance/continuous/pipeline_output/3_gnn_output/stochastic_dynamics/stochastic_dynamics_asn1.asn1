StochasticContinuousDynamicsAgent-Schema DEFINITIONS AUTOMATIC TAGS ::= BEGIN

-- GNN Model Schema Definition
-- Model: Stochastic Continuous Dynamics Agent
-- A continuous-state Active Inference agent whose dynamics carry explicit process
-- and observation noise, rendered as a native linear-Gaussian state-space model
-- (LGSSM). The agent runs passively — it has no control input:
-- - Hidden state x = (position, velocity): the Euler-discretized (dt = 0.1) SDE.
-- - Observation y: two noisy readouts, both reading the position.
-- - Q is the process-noise covariance (inverse process precision); R is the
--   observation-noise covariance (inverse observation precision).

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Stochastic Continuous Dynamics Agent",
    version "1.0",
    annotation "A continuous-state Active Inference agent whose dynamics carry explicit process and observation noise, rendered as a native linear-Gaussian state-space model (LGSSM). The agent runs passively — it has no control input: - Hidden state x = (position, velocity): the Euler-discretized (dt = 0.1) SDE. - Observation y: two noisy readouts, both reading the position. - Q is the process-noise covariance (inverse process precision); R is the   observation-noise covariance (inverse observation precision).",
    variables {
        {
            name "x",
            varType "hidden_state",
            dataType "float"
            dimensions { 2, 1 }
        },
        {
            name "y",
            varType "hidden_state",
            dataType "float"
            dimensions { 2, 1 }
        },
        {
            name "F",
            varType "hidden_state",
            dataType "float"
            dimensions { 2, 2 }
        }
    }
}

END -- StochasticContinuousDynamicsAgent-Schema


-- MODEL_DATA: {"model_name":"Stochastic Continuous Dynamics Agent","version":"1.0","annotation":"A continuous-state Active Inference agent whose dynamics carry explicit process\nand observation noise, rendered as a native linear-Gaussian state-space model\n(LGSSM). The agent runs passively \u2014 it has no control input:\n- Hidden state x = (position, velocity): the Euler-discretized (dt = 0.1) SDE.\n- Observation y: two noisy readouts, both reading the position.\n- Q is the process-noise covariance (inverse process precision); R is the\n  observation-noise covariance (inverse observation precision).","variables":[{"name":"x","var_type":"hidden_state","data_type":"float","dimensions":[2,1],"description":"continuous latent state"},{"name":"y","var_type":"hidden_state","data_type":"float","dimensions":[2,1],"description":"continuous observation"},{"name":"F","var_type":"hidden_state","data_type":"float","dimensions":[2,2],"description":"state transition"},{"name":"H","var_type":"hidden_state","data_type":"float","dimensions":[2,2],"description":"observation matrix"},{"name":"Q","var_type":"hidden_state","data_type":"float","dimensions":[2,2],"description":"process-noise covariance"},{"name":"R","var_type":"hidden_state","data_type":"float","dimensions":[2,2],"description":"observation-noise covariance"},{"name":"prior_mean","var_type":"prior_vector","data_type":"float","dimensions":[2],"description":"prior mean over the initial latent state"},{"name":"prior_cov","var_type":"prior_vector","data_type":"float","dimensions":[2,2],"description":"prior covariance over the initial latent state"},{"name":"t","var_type":"hidden_state","data_type":"integer","dimensions":[1],"description":"discrete time step"}],"connections":[{"annotation":null,"source_variables":["prior_mean"],"target_variables":["x"],"connection_type":"directed","weight":null,"description":null},{"annotation":null,"source_variables":["F"],"target_variables":["x"],"connection_type":"directed","weight":null,"description":null},{"annotation":null,"source_variables":["x"],"target_variables":["y"],"connection_type":"directed","weight":null,"description":null},{"annotation":null,"source_variables":["H"],"target_variables":["y"],"connection_type":"directed","weight":null,"description":null},{"annotation":null,"source_variables":["Q"],"target_variables":["x"],"connection_type":"directed","weight":null,"description":null},{"annotation":null,"source_variables":["R"],"target_variables":["y"],"connection_type":"directed","weight":null,"description":null}],"parameters":[{"name":"F","value":[[1.0,0.1],[0.0,0.9]],"type_hint":null,"description":null},{"name":"H","value":[[1.0,0.0],[1.0,0.0]],"type_hint":null,"description":null},{"name":"Q","value":[[0.1,0.0],[0.0,0.1]],"type_hint":null,"description":null},{"name":"R","value":[[0.2,0.0],[0.0,0.2]],"type_hint":null,"description":null},{"name":"prior_mean","value":[[0.0,0.0]],"type_hint":null,"description":null},{"name":"prior_cov","value":[[0.5,0.0],[0.0,1.0]],"type_hint":null,"description":null},{"name":"num_timesteps","value":15,"type_hint":null,"description":null},{"name":"dt","value":0.1,"type_hint":null,"description":null},{"name":"random_seed","value":42,"type_hint":null,"description":null},{"name":"num_states","value":2,"type_hint":null,"description":null},{"name":"num_observations","value":2,"type_hint":null,"description":null}],"equations":[],"time_specification":{"time_type":"Dynamic","discretization":null,"horizon":15,"step_size":null},"ontology_mappings":[{"variable_name":"F","ontology_term":"StateTransitionMatrix","description":null},{"variable_name":"H","ontology_term":"ObservationMatrix","description":null},{"variable_name":"Q","ontology_term":"ProcessNoiseCovariance","description":null},{"variable_name":"R","ontology_term":"ObservationNoiseCovariance","description":null},{"variable_name":"prior_mean","ontology_term":"PriorMean","description":null},{"variable_name":"prior_cov","ontology_term":"PriorCovariance","description":null},{"variable_name":"x","ontology_term":"ContinuousHiddenState","description":null},{"variable_name":"y","ontology_term":"ContinuousObservation","description":null},{"variable_name":"t","ontology_term":"Time","description":null}]}
