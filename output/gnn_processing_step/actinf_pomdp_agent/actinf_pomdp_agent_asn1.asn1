ClassicActiveInferencePOMDPAgentv1-Schema DEFINITIONS AUTOMATIC TAGS ::= BEGIN

-- GNN Model Schema Definition
-- Model: Classic Active Inference POMDP Agent v1

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Classic Active Inference POMDP Agent v1",
    version "1.0",
    variables {
        {
            name "A",
            varType "likelihood_matrix",
            dataType "float"
            dimensions { 3, 3 }
        },
        {
            name "B",
            varType "transition_matrix",
            dataType "float"
            dimensions { 3, 3, 3 }
        },
        {
            name "C",
            varType "preference_vector",
            dataType "float"
            dimensions { 3 }
        }
    }
}

END -- ClassicActiveInferencePOMDPAgentv1-Schema


-- MODEL_DATA: {"model_name":"Classic Active Inference POMDP Agent v1","version":"1.0","annotation":"","variables":[{"name":"A","var_type":"likelihood_matrix","data_type":"float","dimensions":[3,3],"description":"likelihood_matrix"},{"name":"B","var_type":"transition_matrix","data_type":"float","dimensions":[3,3,3],"description":"transition_matrix"},{"name":"C","var_type":"preference_vector","data_type":"float","dimensions":[3],"description":"preference_vector"},{"name":"D","var_type":"prior_vector","data_type":"float","dimensions":[3],"description":"prior_vector"},{"name":"E","var_type":"policy","data_type":"float","dimensions":[3],"description":"policy"}],"connections":[{"source_variables":["A"],"target_variables":["s"],"connection_type":"directed","weight":null,"description":null},{"source_variables":["B"],"target_variables":["s_prime"],"connection_type":"directed","weight":null,"description":null},{"source_variables":["C"],"target_variables":["o"],"connection_type":"directed","weight":null,"description":null},{"source_variables":["D"],"target_variables":["s"],"connection_type":"directed","weight":null,"description":null},{"source_variables":["E"],"target_variables":["\u03c0"],"connection_type":"directed","weight":null,"description":null},{"source_variables":["s"],"target_variables":["o"],"connection_type":"directed","weight":null,"description":null},{"source_variables":["\u03c0"],"target_variables":["u"],"connection_type":"directed","weight":null,"description":null},{"source_variables":["u"],"target_variables":["s_prime"],"connection_type":"directed","weight":null,"description":null}],"parameters":[{"name":"A","value":[],"type_hint":null,"description":null},{"name":"B","value":[],"type_hint":null,"description":null},{"name":"C","value":[],"type_hint":null,"description":null},{"name":"D","value":[],"type_hint":null,"description":null},{"name":"E","value":[],"type_hint":null,"description":null}],"equations":[],"time_specification":{},"ontology_mappings":[]}
