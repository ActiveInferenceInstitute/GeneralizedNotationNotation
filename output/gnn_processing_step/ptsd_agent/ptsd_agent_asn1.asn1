PTSDHierarchicalActiveInferenceAgent-Schema DEFINITIONS AUTOMATIC TAGS ::= BEGIN

-- GNN Model Schema Definition
-- Model: PTSD Hierarchical Active Inference Agent
-- This hierarchical Active Inference agent consists of two levels:
-- 
-- - **Lower Level Agent**: Processes sensorimotor information including trustworthiness, card states, affect, choices, and game stages
-- - **Higher Level Agent**: Processes abstract safety concepts (self, world, other) based on lower-level posteriors
-- 
-- The agents communicate bidirectionally: lower-level posteriors become higher-level observations, and higher-level inferred states become lower-level priors.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "PTSD Hierarchical Active Inference Agent",
    version "1.0",
    annotation "This hierarchical Active Inference agent consists of two levels:  - **Lower Level Agent**: Processes sensorimotor information including trustworthiness, card states, affect, choices, and game stages - **Higher Level Agent**: Processes abstract safety concepts (self, world, other) based on lower-level posteriors  The agents communicate bidirectionally: lower-level posteriors become higher-level observations, and higher-level inferred states become lower-level priors.",
    variables {
        {
            name "Trustworthiness",
            varType "hidden_state",
            dataType "float"
            dimensions { 2 }
        },
        {
            name "CorrectCard",
            varType "hidden_state",
            dataType "float"
            dimensions { 2 }
        },
        {
            name "Affect",
            varType "action",
            dataType "float"
            dimensions { 2 }
        }
    }
}

END -- PTSDHierarchicalActiveInferenceAgent-Schema


-- MODEL_DATA: {"model_name":"PTSD Hierarchical Active Inference Agent","version":"1.0","annotation":"This hierarchical Active Inference agent consists of two levels:\n\n- **Lower Level Agent**: Processes sensorimotor information including trustworthiness, card states, affect, choices, and game stages\n- **Higher Level Agent**: Processes abstract safety concepts (self, world, other) based on lower-level posteriors\n\nThe agents communicate bidirectionally: lower-level posteriors become higher-level observations, and higher-level inferred states become lower-level priors.","variables":[{"name":"Trustworthiness","var_type":"hidden_state","data_type":"float","dimensions":[2],"description":"Hidden state: trust, distrust"},{"name":"CorrectCard","var_type":"hidden_state","data_type":"float","dimensions":[2],"description":"Hidden state: blue, green"},{"name":"Affect","var_type":"action","data_type":"float","dimensions":[2],"description":"Hidden state: angry, calm"},{"name":"Choice","var_type":"hidden_state","data_type":"float","dimensions":[3],"description":"Hidden state: blue, green, null"},{"name":"Stage","var_type":"hidden_state","data_type":"float","dimensions":[3],"description":"Hidden state: null, advice, decision"},{"name":"Advice","var_type":"action","data_type":"float","dimensions":[3],"description":"Observation: blue, green, null"},{"name":"Feedback","var_type":"hidden_state","data_type":"float","dimensions":[3],"description":"Observation: correct, incorrect, null"},{"name":"Arousal","var_type":"action","data_type":"float","dimensions":[2],"description":"Observation: high, low"},{"name":"ChoiceObs","var_type":"observation","data_type":"float","dimensions":[3],"description":"Observation: blue, green, null"},{"name":"TrustActions","var_type":"action","data_type":"float","dimensions":[2],"description":"Actions: trust, distrust"},{"name":"CardActions","var_type":"action","data_type":"float","dimensions":[3],"description":"Actions: blue, green, null"},{"name":"NullActions","var_type":"action","data_type":"float","dimensions":[1],"description":"Actions: NULL"},{"name":"SafetySelf","var_type":"hidden_state","data_type":"float","dimensions":[2],"description":"Hidden state: safe, danger"},{"name":"SafetyWorld","var_type":"hidden_state","data_type":"float","dimensions":[2],"description":"Hidden state: safe, danger"},{"name":"SafetyOther","var_type":"hidden_state","data_type":"float","dimensions":[2],"description":"Hidden state: safe, danger"},{"name":"TrustworthinessObs","var_type":"observation","data_type":"float","dimensions":[2],"description":"Observation from lower level"},{"name":"CorrectCardObs","var_type":"observation","data_type":"float","dimensions":[2],"description":"Observation from lower level"},{"name":"AffectObs","var_type":"action","data_type":"float","dimensions":[2],"description":"Observation from lower level"},{"name":"ChoiceObsHigher","var_type":"observation","data_type":"float","dimensions":[3],"description":"Observation from lower level"},{"name":"StageObs","var_type":"hidden_state","data_type":"float","dimensions":[3],"description":"Observation from lower level"},{"name":"NullActionsHigher","var_type":"action","data_type":"float","dimensions":[1],"description":"Actions: NULL"}],"connections":[{"source_variables":["Trustworthiness"],"target_variables":["Advice"],"connection_type":"directed","weight":null,"description":"Trust influences advice"},{"source_variables":["CorrectCard"],"target_variables":["Feedback"],"connection_type":"directed","weight":null,"description":"Card state influences feedback"},{"source_variables":["Affect"],"target_variables":["Arousal"],"connection_type":"directed","weight":null,"description":"Affect influences arousal"},{"source_variables":["Choice"],"target_variables":["ChoiceObs"],"connection_type":"directed","weight":null,"description":"Choice influences choice observation"},{"source_variables":["Stage"],"target_variables":["Advice"],"connection_type":"directed","weight":null,"description":"Stage influences advice availability"},{"source_variables":["SafetySelf"],"target_variables":["TrustworthinessObs"],"connection_type":"directed","weight":null,"description":"Safety influences trust observation"},{"source_variables":["SafetyWorld"],"target_variables":["CorrectCardObs"],"connection_type":"directed","weight":null,"description":"World safety influences card observation"},{"source_variables":["SafetyOther"],"target_variables":["AffectObs"],"connection_type":"directed","weight":null,"description":"Other safety influences affect observation"},{"source_variables":["Trustworthiness"],"target_variables":["TrustworthinessObs"],"connection_type":"directed","weight":null,"description":"Lower to higher level mapping"},{"source_variables":["CorrectCard"],"target_variables":["CorrectCardObs"],"connection_type":"directed","weight":null,"description":"Lower to higher level mapping"},{"source_variables":["Affect"],"target_variables":["AffectObs"],"connection_type":"directed","weight":null,"description":"Lower to higher level mapping"},{"source_variables":["Choice"],"target_variables":["ChoiceObsHigher"],"connection_type":"directed","weight":null,"description":"Lower to higher level mapping"},{"source_variables":["Stage"],"target_variables":["StageObs"],"connection_type":"directed","weight":null,"description":"Lower to higher level mapping"}],"parameters":[{"name":"A_lower_0","value":[[0.9,0.1,0.0],[0.1,0.9,0.0],[0.0,0.0,1.0]],"type_hint":null,"description":null},{"name":"A_lower_1","value":[[0.9,0.1,0.0],[0.1,0.9,0.0],[0.0,0.0,1.0]],"type_hint":null,"description":null},{"name":"A_lower_2","value":[[1.0,0.0],[0.0,1.0]],"type_hint":null,"description":null},{"name":"A_lower_3","value":[[1.0,0.0,0.0],[0.0,1.0,0.0],[0.0,0.0,1.0]],"type_hint":null,"description":null},{"name":"B_lower_0","value":[[0.9,0.1],[0.1,0.9]],"type_hint":null,"description":null},{"name":"B_lower_1","value":[[0.9,0.1],[0.1,0.9]],"type_hint":null,"description":null},{"name":"B_lower_2","value":[[0.3333,0.6667],[0.6667,0.3333]],"type_hint":null,"description":null},{"name":"B_lower_3","value":[[0.95,0.025,0.025],[0.025,0.95,0.025],[0.025,0.025,0.95]],"type_hint":null,"description":null},{"name":"B_lower_4","value":[[0.0,1.0,0.0],[0.0,0.0,1.0],[1.0,0.0,0.0]],"type_hint":null,"description":null},{"name":"C_lower_0","value":[0.3333,0.3333,0.3333],"type_hint":null,"description":null},{"name":"C_lower_1","value":[0.5,-3.5,0.0],"type_hint":null,"description":null},{"name":"C_lower_2","value":[0.65,0.35],"type_hint":null,"description":null},{"name":"C_lower_3","value":[0.3333,0.3333,0.3333],"type_hint":null,"description":null},{"name":"D_lower_0","value":[0.5,0.5],"type_hint":null,"description":null},{"name":"D_lower_1","value":[0.5,0.5],"type_hint":null,"description":null},{"name":"D_lower_2","value":[0.5,0.5],"type_hint":null,"description":null},{"name":"D_lower_3","value":[0.0,0.0,1.0],"type_hint":null,"description":null},{"name":"D_lower_4","value":[1.0,0.0,0.0],"type_hint":null,"description":null},{"name":"E_lower","value":[0.0,0.0,0.0,0.0,0.0,0.0],"type_hint":null,"description":null},{"name":"A2_higher_0","value":[[0.667,0.333],[0.333,0.667]],"type_hint":null,"description":null},{"name":"A2_higher_1","value":[[0.5,0.5],[0.5,0.5]],"type_hint":null,"description":null},{"name":"A2_higher_2","value":[[0.333,0.667],[0.667,0.333]],"type_hint":null,"description":null},{"name":"A2_higher_3","value":[[0.333,0.333,0.333],[0.333,0.333,0.333]],"type_hint":null,"description":null},{"name":"A2_higher_4","value":[[0.333,0.333,0.333],[0.333,0.333,0.333]],"type_hint":null,"description":null},{"name":"B2_higher_0","value":[[1.0,0.0],[0.0,1.0]],"type_hint":null,"description":null},{"name":"B2_higher_1","value":[[1.0,0.0],[0.0,1.0]],"type_hint":null,"description":null},{"name":"B2_higher_2","value":[[1.0,0.0],[0.0,1.0]],"type_hint":null,"description":null},{"name":"C2_higher_0","value":[0.5,0.5],"type_hint":null,"description":null},{"name":"C2_higher_1","value":[0.5,0.5],"type_hint":null,"description":null},{"name":"C2_higher_2","value":[1.0,0.0],"type_hint":null,"description":null},{"name":"C2_higher_3","value":[0.333,0.333,0.333],"type_hint":null,"description":null},{"name":"C2_higher_4","value":[0.333,0.333,0.333],"type_hint":null,"description":null},{"name":"D2_higher_0","value":[0.25,0.75],"type_hint":null,"description":null},{"name":"D2_higher_1","value":[0.25,0.75],"type_hint":null,"description":null},{"name":"D2_higher_2","value":[0.25,0.75],"type_hint":null,"description":null},{"name":"E2_higher","value":[0.0],"type_hint":null,"description":null},{"name":"pA_lower","value":1.0,"type_hint":null,"description":null},{"name":"pB_lower","value":1.0,"type_hint":null,"description":null},{"name":"pD_lower","value":1.0,"type_hint":null,"description":null},{"name":"pA2_higher","value":1.0,"type_hint":null,"description":null},{"name":"pB2_higher","value":1.0,"type_hint":null,"description":null},{"name":"pD2_higher","value":1.0,"type_hint":null,"description":null},{"name":"p_advice","value":0.9,"type_hint":null,"description":null},{"name":"alpha","value":0.9,"type_hint":null,"description":null},{"name":"p_Btrust","value":0.9,"type_hint":null,"description":null},{"name":"p_Bcorrectcard","value":0.9,"type_hint":null,"description":null},{"name":"p_Bchoice","value":0.95,"type_hint":null,"description":null},{"name":"p_Bstage","value":1.0,"type_hint":null,"description":null},{"name":"cc","value":0.5,"type_hint":null,"description":null},{"name":"arousal_low_preference","value":0.35,"type_hint":null,"description":null},{"name":"trust_safety_association","value":0.667,"type_hint":null,"description":null},{"name":"affect_safety_association","value":0.667,"type_hint":null,"description":null},{"name":"prior_on_danger","value":0.75,"type_hint":null,"description":null},{"name":"gamma","value":16.0,"type_hint":null,"description":null},{"name":"alpha_policy","value":16.0,"type_hint":null,"description":null}],"equations":[{"label":null,"content":"F = D_KL[Q(s)||P(s|o)] - ln P(o)                                   # Free Energy Q(s) = softmax(ln A + ln B + ln C + ln D)                          # Variational Message Passing \u03c0* = argmin_\u03c0 F(\u03c0)                                                  # Policy Selection","format":"latex","description":null},{"label":null,"content":"F_high = D_KL[Q(s_high)||P(s_high|o_high)] - ln P(o_high)         # Free Energy Q(s_high) = softmax(ln A_high + ln B_high + ln C_high + ln D_high) # Hierarchical Inference o_high = f(Q_low(s_low))                                            # Inter-level Coupling","format":"latex","description":null}],"time_specification":{"time_type":"Static","discretization":null,"horizon":null,"step_size":null},"ontology_mappings":[]}
