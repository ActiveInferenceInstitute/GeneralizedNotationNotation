GNN-Model DEFINITIONS ::= BEGIN

GNNModel ::= SEQUENCE {
    modelName     IA5String,
    version       IA5String,
    annotation    IA5String,
    variables     SEQUENCE OF Variable,
    connections   SEQUENCE OF Connection,
    parameters    SEQUENCE OF Parameter
}

Variable ::= SEQUENCE {
    name          IA5String,
    type          IA5String,
    dimensions    SEQUENCE OF INTEGER,
    description   IA5String
}

Connection ::= SEQUENCE {
    source        IA5String,
    target        IA5String,
    type          IA5String,
    description   IA5String
}

Parameter ::= SEQUENCE {
    name          IA5String,
    value         IA5String,
    description   IA5String
}

END
