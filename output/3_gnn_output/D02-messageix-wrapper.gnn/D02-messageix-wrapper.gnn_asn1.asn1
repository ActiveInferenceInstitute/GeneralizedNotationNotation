MESSAGEixNationalWrapperBlanket-Schema DEFINITIONS AUTOMATIC TAGS ::= BEGIN

-- GNN Model Schema Definition
-- Model: MESSAGEix National Wrapper Blanket
-- Markov blanket for MESSAGEix as a coupled component in NEST Stage 1.
-- 
-- Boundary scope: this blanket is drawn around MODEL ↔ NEST PLATFORM. Of the
-- active states, only p crosses onward to the coupled model (STURM); e and J
-- are active toward the platform (gates, monitoring, convergence accounting)
-- and never reach STURM. cap arrives as an imposed constraint — the HIERARCHY
-- regime of PR #87 Q-13; the D03 (STURM) blanket has no counterpart input.
-- 
-- Scope vs Q1 (Technical_Responses_Draft_v1): this file specifies the wrapper's
-- model-level I/O blanket — Q1 functions #1–#3. Q1 function #4 (the Active
-- Inference latent-summary layer: distilling raw outputs into belief variables
-- such as decarbonization rate, via RxInfer) is deliberately NOT modeled here;
-- those latent states are the factor-graph deliverables (D04, D07), which will
-- sit behind this blanket's internal side.
-- 
-- - Sensory states: what crosses INTO the model — demand trajectories per commodity (from the building-stock side) and policy constraints (emissions cap).
-- - Active states: what crosses OUT — commodity shadow prices (PRICE_COMMODITY duals), total emissions, and objective value (see boundary scope above).
-- - Internal states: capacities, dispatch, and the LP solution machinery — never exchanged.
-- - Every exchanged variable carries the declared boundary fields (PR #80 §4 / PR #95): unit · convention · temporal support · spatial support. Prices carry the engine's annualisation convention; demand carries its allocation basis. Spatial support follows the D05 memo (res-5 exchange via declared crosswalk).
-- - This is the D02 pattern file; D03 (STURM wrapper) mirrors it with sensory/active reversed on the price/demand pair.
-- - Renderable form: this wrapper is a *structural* blanket (it declares boundary structure, not a generative parameterization), so the GNN step-11 renderer has no renderable form of it as authored — it classifies the spec as a discrete POMDP and fails on the missing `A/B/C/D` (upstream: GeneralizedNotationNotation#111). The renderable instantiation of this blanket is the continuous-exemplar fixture block (`models/active_inference/rxinfer-bridge/fixtures/d04/d04_fixture.gnn.md`), which renders to RxInfer and executes; until the upstream path exists, render the instantiation, not the wrapper.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "MESSAGEix National Wrapper Blanket",
    version "1.0",
    annotation "Markov blanket for MESSAGEix as a coupled component in NEST Stage 1.  Boundary scope: this blanket is drawn around MODEL ↔ NEST PLATFORM. Of the active states, only p crosses onward to the coupled model (STURM); e and J are active toward the platform (gates, monitoring, convergence accounting) and never reach STURM. cap arrives as an imposed constraint — the HIERARCHY regime of PR #87 Q-13; the D03 (STURM) blanket has no counterpart input.  Scope vs Q1 (Technical_Responses_Draft_v1): this file specifies the wrapper's model-level I/O blanket — Q1 functions #1–#3. Q1 function #4 (the Active Inference latent-summary layer: distilling raw outputs into belief variables such as decarbonization rate, via RxInfer) is deliberately NOT modeled here; those latent states are the factor-graph deliverables (D04, D07), which will sit behind this blanket's internal side.  - Sensory states: what crosses INTO the model — demand trajectories per commodity (from the building-stock side) and policy constraints (emissions cap). - Active states: what crosses OUT — commodity shadow prices (PRICE_COMMODITY duals), total emissions, and objective value (see boundary scope above). - Internal states: capacities, dispatch, and the LP solution machinery — never exchanged. - Every exchanged variable carries the declared boundary fields (PR #80 §4 / PR #95): unit · convention · temporal support · spatial support. Prices carry the engine's annualisation convention; demand carries its allocation basis. Spatial support follows the D05 memo (res-5 exchange via declared crosswalk). - This is the D02 pattern file; D03 (STURM wrapper) mirrors it with sensory/active reversed on the price/demand pair. - Renderable form: this wrapper is a *structural* blanket (it declares boundary structure, not a generative parameterization), so the GNN step-11 renderer has no renderable form of it as authored — it classifies the spec as a discrete POMDP and fails on the missing `A/B/C/D` (upstream: GeneralizedNotationNotation#111). The renderable instantiation of this blanket is the continuous-exemplar fixture block (`models/active_inference/rxinfer-bridge/fixtures/d04/d04_fixture.gnn.md`), which renders to RxInfer and executes; until the upstream path exists, render the instantiation, not the wrapper.",
    variables {
        {
            name "d",
            varType "hidden_state",
            dataType "float"
            dimensions { 2, 12 }
        },
        {
            name "cap",
            varType "hidden_state",
            dataType "float"
            dimensions { 1 }
        },
        {
            name "p",
            varType "hidden_state",
            dataType "float"
            dimensions { 2, 12 }
        }
    }
}

END -- MESSAGEixNationalWrapperBlanket-Schema


-- MODEL_DATA: {"model_name":"MESSAGEix National Wrapper Blanket","version":"1.0","annotation":"Markov blanket for MESSAGEix as a coupled component in NEST Stage 1.\n\nBoundary scope: this blanket is drawn around MODEL \u2194 NEST PLATFORM. Of the\nactive states, only p crosses onward to the coupled model (STURM); e and J\nare active toward the platform (gates, monitoring, convergence accounting)\nand never reach STURM. cap arrives as an imposed constraint \u2014 the HIERARCHY\nregime of PR #87 Q-13; the D03 (STURM) blanket has no counterpart input.\n\nScope vs Q1 (Technical_Responses_Draft_v1): this file specifies the wrapper's\nmodel-level I/O blanket \u2014 Q1 functions #1\u2013#3. Q1 function #4 (the Active\nInference latent-summary layer: distilling raw outputs into belief variables\nsuch as decarbonization rate, via RxInfer) is deliberately NOT modeled here;\nthose latent states are the factor-graph deliverables (D04, D07), which will\nsit behind this blanket's internal side.\n\n- Sensory states: what crosses INTO the model \u2014 demand trajectories per commodity (from the building-stock side) and policy constraints (emissions cap).\n- Active states: what crosses OUT \u2014 commodity shadow prices (PRICE_COMMODITY duals), total emissions, and objective value (see boundary scope above).\n- Internal states: capacities, dispatch, and the LP solution machinery \u2014 never exchanged.\n- Every exchanged variable carries the declared boundary fields (PR #80 \u00a74 / PR #95): unit \u00b7 convention \u00b7 temporal support \u00b7 spatial support. Prices carry the engine's annualisation convention; demand carries its allocation basis. Spatial support follows the D05 memo (res-5 exchange via declared crosswalk).\n- This is the D02 pattern file; D03 (STURM wrapper) mirrors it with sensory/active reversed on the price/demand pair.\n- Renderable form: this wrapper is a *structural* blanket (it declares boundary structure, not a generative parameterization), so the GNN step-11 renderer has no renderable form of it as authored \u2014 it classifies the spec as a discrete POMDP and fails on the missing `A/B/C/D` (upstream: GeneralizedNotationNotation#111). The renderable instantiation of this blanket is the continuous-exemplar fixture block (`models/active_inference/rxinfer-bridge/fixtures/d04/d04_fixture.gnn.md`), which renders to RxInfer and executes; until the upstream path exists, render the instantiation, not the wrapper.","variables":[{"name":"d","var_type":"hidden_state","data_type":"float","dimensions":[2,12],"description":"demand per commodity per time slice [GWh; basis-allocated; temporal support: 12 slices]"},{"name":"cap","var_type":"hidden_state","data_type":"float","dimensions":[1],"description":"emissions cap [t CO2/yr; policy constraint]"},{"name":"p","var_type":"hidden_state","data_type":"float","dimensions":[2,12],"description":"PRICE_COMMODITY duals [USD/MWh; carries annualisation convention]"},{"name":"e","var_type":"hidden_state","data_type":"float","dimensions":[1],"description":"total emissions [t CO2/yr]"},{"name":"J","var_type":"hidden_state","data_type":"float","dimensions":[1],"description":"objective value [USD; convention-laden]"},{"name":"K","var_type":"hidden_state","data_type":"float","dimensions":[4],"description":"installed capacity per technology [MW]"},{"name":"x","var_type":"hidden_state","data_type":"float","dimensions":[4,12],"description":"dispatch per technology per slice [MWh]"},{"name":"s","var_type":"hidden_state","data_type":"float","dimensions":[8,1],"description":"internal solver state summary (basis, duals machinery)"},{"name":"t","var_type":"hidden_state","data_type":"integer","dimensions":[1],"description":"coupling iteration index"}],"connections":[{"source_variables":["d"],"target_variables":["s"],"connection_type":"directed","weight":null,"description":null},{"source_variables":["cap"],"target_variables":["s"],"connection_type":"directed","weight":null,"description":null},{"source_variables":["s"],"target_variables":["K"],"connection_type":"directed","weight":null,"description":null},{"source_variables":["s"],"target_variables":["x"],"connection_type":"directed","weight":null,"description":null},{"source_variables":["K"],"target_variables":["p"],"connection_type":"directed","weight":null,"description":null},{"source_variables":["x"],"target_variables":["p"],"connection_type":"directed","weight":null,"description":null},{"source_variables":["x"],"target_variables":["e"],"connection_type":"directed","weight":null,"description":null},{"source_variables":["s"],"target_variables":["J"],"connection_type":"directed","weight":null,"description":null},{"source_variables":["p"],"target_variables":["d"],"connection_type":"directed","weight":null,"description":null}],"parameters":[{"name":"d","value":[[0.0,0.0]],"type_hint":null,"description":null},{"name":"cap","value":[[200000.0]],"type_hint":null,"description":null},{"name":"num_commodities","value":2,"type_hint":null,"description":null},{"name":"num_time_slices","value":12,"type_hint":null,"description":null},{"name":"num_technologies","value":4,"type_hint":null,"description":null},{"name":"num_regions","value":1,"type_hint":null,"description":null}],"equations":[],"time_specification":{"time_type":"Dynamic","discretization":"DiscreteTime","horizon":"Unbounded","step_size":null},"ontology_mappings":[{"variable_name":"d","ontology_term":"Observation","description":null},{"variable_name":"cap","ontology_term":"Observation","description":null},{"variable_name":"p","ontology_term":"Action","description":null},{"variable_name":"e","ontology_term":"Action","description":null},{"variable_name":"J","ontology_term":"Action","description":null},{"variable_name":"K","ontology_term":"HiddenState","description":null},{"variable_name":"x","ontology_term":"HiddenState","description":null},{"variable_name":"s","ontology_term":"HiddenState","description":null},{"variable_name":"t","ontology_term":"Time","description":null}]}
