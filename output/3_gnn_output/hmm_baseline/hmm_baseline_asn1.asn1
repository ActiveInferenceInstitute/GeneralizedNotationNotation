HiddenMarkovModelBaseline-Schema DEFINITIONS AUTOMATIC TAGS ::= BEGIN

-- GNN Model Schema Definition
-- Model: Hidden Markov Model Baseline
-- A standard discrete Hidden Markov Model with:
-- - 4 hidden states with Markovian dynamics
-- - 6 observation symbols
-- - Fixed transition and emission matrices
-- - No action selection (passive inference only)
-- - Suitable for sequence modeling and state estimation tasks

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Hidden Markov Model Baseline",
    version "1.0",
    annotation "A standard discrete Hidden Markov Model with: - 4 hidden states with Markovian dynamics - 6 observation symbols - Fixed transition and emission matrices - No action selection (passive inference only) - Suitable for sequence modeling and state estimation tasks",
    variables {
        {
            name "A",
            varType "likelihood_matrix",
            dataType "float"
            dimensions { 6, 4 }
        },
        {
            name "B",
            varType "transition_matrix",
            dataType "float"
            dimensions { 4, 4 }
        },
        {
            name "D",
            varType "prior_vector",
            dataType "float"
            dimensions { 4 }
        }
    }
}

END -- HiddenMarkovModelBaseline-Schema


-- MODEL_DATA: {"model_name":"Hidden Markov Model Baseline","version":"1.0","annotation":"A standard discrete Hidden Markov Model with:\n- 4 hidden states with Markovian dynamics\n- 6 observation symbols\n- Fixed transition and emission matrices\n- No action selection (passive inference only)\n- Suitable for sequence modeling and state estimation tasks","variables":[{"name":"A","var_type":"likelihood_matrix","data_type":"float","dimensions":[6,4],"description":"Emission matrix: observations x hidden states"},{"name":"B","var_type":"transition_matrix","data_type":"float","dimensions":[4,4],"description":"Transition matrix (no action dependence)"},{"name":"D","var_type":"prior_vector","data_type":"float","dimensions":[4],"description":"Initial state distribution (prior)"},{"name":"s","var_type":"hidden_state","data_type":"float","dimensions":[4,1],"description":"Hidden state belief (posterior)"},{"name":"s_prime","var_type":"hidden_state","data_type":"float","dimensions":[4,1],"description":"Next hidden state"},{"name":"o","var_type":"observation","data_type":"integer","dimensions":[6,1],"description":"Current observation (one-hot)"},{"name":"F","var_type":"hidden_state","data_type":"float","dimensions":[1],"description":"Variational Free Energy (negative ELBO)"},{"name":"alpha","var_type":"action","data_type":"float","dimensions":[4,1],"description":"Forward variable (belief propagation)"},{"name":"beta","var_type":"hidden_state","data_type":"float","dimensions":[4,1],"description":"Backward variable"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["s"],"target_variables":["s_prime"],"connection_type":"directed","weight":null,"description":null},{"annotation":null,"source_variables":["A"],"target_variables":["o"],"connection_type":"undirected","weight":null,"description":null},{"annotation":null,"source_variables":["B"],"target_variables":["s_prime"],"connection_type":"directed","weight":null,"description":null},{"annotation":null,"source_variables":["s"],"target_variables":["B"],"connection_type":"undirected","weight":null,"description":null},{"annotation":null,"source_variables":["s"],"target_variables":["F"],"connection_type":"undirected","weight":null,"description":null},{"annotation":null,"source_variables":["o"],"target_variables":["F"],"connection_type":"undirected","weight":null,"description":null},{"annotation":null,"source_variables":["s"],"target_variables":["alpha"],"connection_type":"undirected","weight":null,"description":null},{"annotation":null,"source_variables":["o"],"target_variables":["alpha"],"connection_type":"undirected","weight":null,"description":null},{"annotation":null,"source_variables":["alpha"],"target_variables":["s_prime"],"connection_type":"directed","weight":null,"description":null},{"annotation":null,"source_variables":["s_prime"],"target_variables":["beta"],"connection_type":"undirected","weight":null,"description":null}],"parameters":[{"name":"A","value":[[0.7,0.1,0.1,0.1],[0.1,0.7,0.1,0.1],[0.1,0.1,0.7,0.1],[0.1,0.1,0.1,0.7],[0.1,0.1,0.4,0.4],[0.4,0.4,0.1,0.1]],"type_hint":null,"description":null},{"name":"B","value":[[0.7,0.1,0.1,0.1],[0.1,0.7,0.2,0.1],[0.1,0.1,0.6,0.2],[0.1,0.1,0.1,0.6]],"type_hint":null,"description":null},{"name":"D","value":[[0.25,0.25,0.25,0.25]],"type_hint":null,"description":null},{"name":"num_hidden_states","value":4,"type_hint":null,"description":null},{"name":"num_observations","value":6,"type_hint":null,"description":null},{"name":"num_timesteps","value":50,"type_hint":null,"description":null}],"equations":[],"time_specification":{"time_type":"Dynamic","discretization":null,"horizon":"Unbounded","step_size":null},"ontology_mappings":[{"variable_name":"A","ontology_term":"EmissionMatrix","description":null},{"variable_name":"B","ontology_term":"TransitionMatrix","description":null},{"variable_name":"D","ontology_term":"InitialStateDistribution","description":null},{"variable_name":"s","ontology_term":"HiddenState","description":null},{"variable_name":"s_prime","ontology_term":"NextHiddenState","description":null},{"variable_name":"o","ontology_term":"Observation","description":null},{"variable_name":"F","ontology_term":"VariationalFreeEnergy","description":null},{"variable_name":"alpha","ontology_term":"ForwardVariable","description":null},{"variable_name":"beta","ontology_term":"BackwardVariable","description":null},{"variable_name":"t","ontology_term":"Time","description":null}]}
