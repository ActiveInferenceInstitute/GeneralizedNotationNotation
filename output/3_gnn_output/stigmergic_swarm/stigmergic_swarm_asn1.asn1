StigmergicSwarmActiveInference-Schema DEFINITIONS AUTOMATIC TAGS ::= BEGIN

-- GNN Model Schema Definition
-- Model: Stigmergic Swarm Active Inference
-- Three Active Inference agents coordinating via stigmergy (environmental traces):
-- 
-- - No direct communication between agents — coordination emerges from environment
-- - Agents deposit and sense environmental signals (pheromone analogy)
-- - Shared 3x3 grid environment with signal intensity at each cell
-- - Each agent navigates independently while responding to accumulated signals
-- - Signal deposition: actions leave traces that other agents can observe
-- - Signal decay: environmental signals decay over time (volatility)
-- - Demonstrates emergent collective behavior from individual free energy minimization
-- - Models ant colony foraging, distributed robotics, and decentralized coordination

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Stigmergic Swarm Active Inference",
    version "1.0",
    annotation "Three Active Inference agents coordinating via stigmergy (environmental traces):  - No direct communication between agents — coordination emerges from environment - Agents deposit and sense environmental signals (pheromone analogy) - Shared 3x3 grid environment with signal intensity at each cell - Each agent navigates independently while responding to accumulated signals - Signal deposition: actions leave traces that other agents can observe - Signal decay: environmental signals decay over time (volatility) - Demonstrates emergent collective behavior from individual free energy minimization - Models ant colony foraging, distributed robotics, and decentralized coordination",
    variables {
        {
            name "A_agent1",
            varType "action",
            dataType "float"
            dimensions { 4, 9 }
        },
        {
            name "B_agent1",
            varType "hidden_state",
            dataType "float"
            dimensions { 9, 9, 4 }
        },
        {
            name "C_agent1",
            varType "hidden_state",
            dataType "float"
            dimensions { 4 }
        }
    }
}

END -- StigmergicSwarmActiveInference-Schema


-- MODEL_DATA: {"model_name":"Stigmergic Swarm Active Inference","version":"1.0","annotation":"Three Active Inference agents coordinating via stigmergy (environmental traces):\n\n- No direct communication between agents \u2014 coordination emerges from environment\n- Agents deposit and sense environmental signals (pheromone analogy)\n- Shared 3x3 grid environment with signal intensity at each cell\n- Each agent navigates independently while responding to accumulated signals\n- Signal deposition: actions leave traces that other agents can observe\n- Signal decay: environmental signals decay over time (volatility)\n- Demonstrates emergent collective behavior from individual free energy minimization\n- Models ant colony foraging, distributed robotics, and decentralized coordination","variables":[{"name":"A_agent1","var_type":"action","data_type":"float","dimensions":[4,9],"description":"Agent 1 likelihood: P(obs | position on 3x3 grid)"},{"name":"B_agent1","var_type":"hidden_state","data_type":"float","dimensions":[9,9,4],"description":"Agent 1 transitions: (9 positions \u00d7 4 actions: N/S/E/W)"},{"name":"C_agent1","var_type":"hidden_state","data_type":"float","dimensions":[4],"description":"Agent 1 preferences over observations"},{"name":"D_agent1","var_type":"hidden_state","data_type":"float","dimensions":[9],"description":"Agent 1 position prior"},{"name":"s_agent1","var_type":"hidden_state","data_type":"float","dimensions":[9,1],"description":"Agent 1 position belief (9 grid cells)"},{"name":"o_agent1","var_type":"observation","data_type":"integer","dimensions":[4,1],"description":"Agent 1 observation: (empty, signal_low, signal_high, goal)"},{"name":"pi1","var_type":"policy","data_type":"float","dimensions":[4],"description":"Agent 1 policy"},{"name":"u_agent1","var_type":"action","data_type":"integer","dimensions":[1],"description":"Agent 1 action"},{"name":"G1","var_type":"hidden_state","data_type":"float","dimensions":[1],"description":"Agent 1 EFE"},{"name":"A_agent2","var_type":"action","data_type":"float","dimensions":[4,9],"description":"Agent 2 likelihood"},{"name":"B_agent2","var_type":"hidden_state","data_type":"float","dimensions":[9,9,4],"description":"Agent 2 transitions"},{"name":"C_agent2","var_type":"hidden_state","data_type":"float","dimensions":[4],"description":"Agent 2 preferences"},{"name":"D_agent2","var_type":"hidden_state","data_type":"float","dimensions":[9],"description":"Agent 2 position prior"},{"name":"s_agent2","var_type":"hidden_state","data_type":"float","dimensions":[9,1],"description":"Agent 2 position belief"},{"name":"o_agent2","var_type":"observation","data_type":"integer","dimensions":[4,1],"description":"Agent 2 observation"},{"name":"pi2","var_type":"policy","data_type":"float","dimensions":[4],"description":"Agent 2 policy"},{"name":"u_agent2","var_type":"action","data_type":"integer","dimensions":[1],"description":"Agent 2 action"},{"name":"G2","var_type":"hidden_state","data_type":"float","dimensions":[1],"description":"Agent 2 EFE"},{"name":"A_agent3","var_type":"action","data_type":"float","dimensions":[4,9],"description":"Agent 3 likelihood"},{"name":"B_agent3","var_type":"hidden_state","data_type":"float","dimensions":[9,9,4],"description":"Agent 3 transitions"},{"name":"C_agent3","var_type":"hidden_state","data_type":"float","dimensions":[4],"description":"Agent 3 preferences"},{"name":"D_agent3","var_type":"hidden_state","data_type":"float","dimensions":[9],"description":"Agent 3 position prior"},{"name":"s_agent3","var_type":"hidden_state","data_type":"float","dimensions":[9,1],"description":"Agent 3 position belief"},{"name":"o_agent3","var_type":"observation","data_type":"integer","dimensions":[4,1],"description":"Agent 3 observation"},{"name":"pi3","var_type":"policy","data_type":"float","dimensions":[4],"description":"Agent 3 policy"},{"name":"u_agent3","var_type":"action","data_type":"integer","dimensions":[1],"description":"Agent 3 action"},{"name":"G3","var_type":"hidden_state","data_type":"float","dimensions":[1],"description":"Agent 3 EFE"},{"name":"env_signal","var_type":"hidden_state","data_type":"float","dimensions":[9,1],"description":"Signal intensity at each grid cell (0.0 to 1.0)"},{"name":"signal_decay","var_type":"hidden_state","data_type":"float","dimensions":[1],"description":"Signal decay rate per timestep"},{"name":"env_obs_likelihood","var_type":"observation","data_type":"float","dimensions":[4,3],"description":"P(obs category | local signal level: none/low/high)"},{"name":"env_signal_prior","var_type":"prior_vector","data_type":"float","dimensions":[3],"description":"prior over local signal level (none/low/high)"},{"name":"signal_seek","var_type":"hidden_state","data_type":"float","dimensions":[1],"description":"signal-seeking gain applied to action selection"},{"name":"t","var_type":"hidden_state","data_type":"integer","dimensions":[1],"description":"Discrete time step"}],"connections":[{"annotation":null,"source_variables":["D_agent1"],"target_variables":["s_agent1"],"connection_type":"directed","weight":null,"description":null},{"annotation":null,"source_variables":["s_agent1"],"target_variables":["A_agent1"],"connection_type":"undirected","weight":null,"description":null},{"annotation":null,"source_variables":["A_agent1"],"target_variables":["o_agent1"],"connection_type":"undirected","weight":null,"description":null},{"annotation":null,"source_variables":["C_agent1"],"target_variables":["G1"],"connection_type":"directed","weight":null,"description":null},{"annotation":null,"source_variables":["G1"],"target_variables":["pi1"],"connection_type":"directed","weight":null,"description":null},{"annotation":null,"source_variables":["pi1"],"target_variables":["u_agent1"],"connection_type":"directed","weight":null,"description":null},{"annotation":null,"source_variables":["B_agent1"],"target_variables":["u_agent1"],"connection_type":"directed","weight":null,"description":null},{"annotation":null,"source_variables":["D_agent2"],"target_variables":["s_agent2"],"connection_type":"directed","weight":null,"description":null},{"annotation":null,"source_variables":["s_agent2"],"target_variables":["A_agent2"],"connection_type":"undirected","weight":null,"description":null},{"annotation":null,"source_variables":["A_agent2"],"target_variables":["o_agent2"],"connection_type":"undirected","weight":null,"description":null},{"annotation":null,"source_variables":["C_agent2"],"target_variables":["G2"],"connection_type":"directed","weight":null,"description":null},{"annotation":null,"source_variables":["G2"],"target_variables":["pi2"],"connection_type":"directed","weight":null,"description":null},{"annotation":null,"source_variables":["pi2"],"target_variables":["u_agent2"],"connection_type":"directed","weight":null,"description":null},{"annotation":null,"source_variables":["B_agent2"],"target_variables":["u_agent2"],"connection_type":"directed","weight":null,"description":null},{"annotation":null,"source_variables":["D_agent3"],"target_variables":["s_agent3"],"connection_type":"directed","weight":null,"description":null},{"annotation":null,"source_variables":["s_agent3"],"target_variables":["A_agent3"],"connection_type":"undirected","weight":null,"description":null},{"annotation":null,"source_variables":["A_agent3"],"target_variables":["o_agent3"],"connection_type":"undirected","weight":null,"description":null},{"annotation":null,"source_variables":["C_agent3"],"target_variables":["G3"],"connection_type":"directed","weight":null,"description":null},{"annotation":null,"source_variables":["G3"],"target_variables":["pi3"],"connection_type":"directed","weight":null,"description":null},{"annotation":null,"source_variables":["pi3"],"target_variables":["u_agent3"],"connection_type":"directed","weight":null,"description":null},{"annotation":null,"source_variables":["B_agent3"],"target_variables":["u_agent3"],"connection_type":"directed","weight":null,"description":null},{"annotation":null,"source_variables":["u_agent1"],"target_variables":["env_signal"],"connection_type":"directed","weight":null,"description":null},{"annotation":null,"source_variables":["u_agent2"],"target_variables":["env_signal"],"connection_type":"directed","weight":null,"description":null},{"annotation":null,"source_variables":["u_agent3"],"target_variables":["env_signal"],"connection_type":"directed","weight":null,"description":null},{"annotation":null,"source_variables":["env_signal"],"target_variables":["A_agent1"],"connection_type":"undirected","weight":null,"description":null},{"annotation":null,"source_variables":["env_signal"],"target_variables":["A_agent2"],"connection_type":"undirected","weight":null,"description":null},{"annotation":null,"source_variables":["env_signal"],"target_variables":["A_agent3"],"connection_type":"undirected","weight":null,"description":null},{"annotation":null,"source_variables":["signal_decay"],"target_variables":["env_signal"],"connection_type":"directed","weight":null,"description":null}],"parameters":[{"name":"A_agent1","value":[[0.7,0.7,0.7,0.7,0.7,0.7,0.7,0.7,0.1],[0.15,0.15,0.15,0.15,0.15,0.15,0.15,0.15,0.1],[0.1,0.1,0.1,0.1,0.1,0.1,0.1,0.1,0.1],[0.05,0.05,0.05,0.05,0.05,0.05,0.05,0.05,0.7]],"type_hint":null,"description":null},{"name":"A_agent2","value":[[0.7,0.7,0.7,0.7,0.7,0.7,0.7,0.7,0.1],[0.15,0.15,0.15,0.15,0.15,0.15,0.15,0.15,0.1],[0.1,0.1,0.1,0.1,0.1,0.1,0.1,0.1,0.1],[0.05,0.05,0.05,0.05,0.05,0.05,0.05,0.05,0.7]],"type_hint":null,"description":null},{"name":"A_agent3","value":[[0.7,0.7,0.7,0.7,0.7,0.7,0.7,0.7,0.1],[0.15,0.15,0.15,0.15,0.15,0.15,0.15,0.15,0.1],[0.1,0.1,0.1,0.1,0.1,0.1,0.1,0.1,0.1],[0.05,0.05,0.05,0.05,0.05,0.05,0.05,0.05,0.7]],"type_hint":null,"description":null},{"name":"C_agent1","value":[[-0.5,0.5,1.5,3.0]],"type_hint":null,"description":null},{"name":"C_agent2","value":[[-0.5,0.5,1.5,3.0]],"type_hint":null,"description":null},{"name":"C_agent3","value":[[-0.5,0.5,1.5,3.0]],"type_hint":null,"description":null},{"name":"D_agent1","value":[[1.0,0.0,0.0,0.0,0.0,0.0,0.0,0.0,0.0]],"type_hint":null,"description":null},{"name":"D_agent2","value":[[0.0,0.0,1.0,0.0,0.0,0.0,0.0,0.0,0.0]],"type_hint":null,"description":null},{"name":"D_agent3","value":[[0.0,0.0,0.0,0.0,0.0,0.0,1.0,0.0,0.0]],"type_hint":null,"description":null},{"name":"B_agent1","value":[[[1.0,0.0,0.0,0.9,0.0,0.0,0.0,0.0,0.0],[0.0,1.0,0.0,0.0,0.9,0.0,0.0,0.0,0.0],[0.0,0.0,1.0,0.0,0.0,0.9,0.0,0.0,0.0],[0.0,0.0,0.0,0.1,0.0,0.0,0.9,0.0,0.0],[0.0,0.0,0.0,0.0,0.1,0.0,0.0,0.9,0.0],[0.0,0.0,0.0,0.0,0.0,0.1,0.0,0.0,0.9],[0.0,0.0,0.0,0.0,0.0,0.0,0.1,0.0,0.0],[0.0,0.0,0.0,0.0,0.0,0.0,0.0,0.1,0.0],[0.0,0.0,0.0,0.0,0.0,0.0,0.0,0.0,0.1]],[[0.1,0.0,0.0,0.0,0.0,0.0,0.0,0.0,0.0],[0.0,0.1,0.0,0.0,0.0,0.0,0.0,0.0,0.0],[0.0,0.0,0.1,0.0,0.0,0.0,0.0,0.0,0.0],[0.9,0.0,0.0,0.1,0.0,0.0,0.0,0.0,0.0],[0.0,0.9,0.0,0.0,0.1,0.0,0.0,0.0,0.0],[0.0,0.0,0.9,0.0,0.0,0.1,0.0,0.0,0.0],[0.0,0.0,0.0,0.9,0.0,0.0,1.0,0.0,0.0],[0.0,0.0,0.0,0.0,0.9,0.0,0.0,1.0,0.0],[0.0,0.0,0.0,0.0,0.0,0.9,0.0,0.0,1.0]],[[0.1,0.0,0.0,0.0,0.0,0.0,0.0,0.0,0.0],[0.9,0.1,0.0,0.0,0.0,0.0,0.0,0.0,0.0],[0.0,0.9,1.0,0.0,0.0,0.0,0.0,0.0,0.0],[0.0,0.0,0.0,0.1,0.0,0.0,0.0,0.0,0.0],[0.0,0.0,0.0,0.9,0.1,0.0,0.0,0.0,0.0],[0.0,0.0,0.0,0.0,0.9,1.0,0.0,0.0,0.0],[0.0,0.0,0.0,0.0,0.0,0.0,0.1,0.0,0.0],[0.0,0.0,0.0,0.0,0.0,0.0,0.9,0.1,0.0],[0.0,0.0,0.0,0.0,0.0,0.0,0.0,0.9,1.0]],[[1.0,0.9,0.0,0.0,0.0,0.0,0.0,0.0,0.0],[0.0,0.1,0.9,0.0,0.0,0.0,0.0,0.0,0.0],[0.0,0.0,0.1,0.0,0.0,0.0,0.0,0.0,0.0],[0.0,0.0,0.0,1.0,0.9,0.0,0.0,0.0,0.0],[0.0,0.0,0.0,0.0,0.1,0.9,0.0,0.0,0.0],[0.0,0.0,0.0,0.0,0.0,0.1,0.0,0.0,0.0],[0.0,0.0,0.0,0.0,0.0,0.0,1.0,0.9,0.0],[0.0,0.0,0.0,0.0,0.0,0.0,0.0,0.1,0.9],[0.0,0.0,0.0,0.0,0.0,0.0,0.0,0.0,0.1]]],"type_hint":null,"description":null},{"name":"B_agent2","value":[[[1.0,0.0,0.0,0.9,0.0,0.0,0.0,0.0,0.0],[0.0,1.0,0.0,0.0,0.9,0.0,0.0,0.0,0.0],[0.0,0.0,1.0,0.0,0.0,0.9,0.0,0.0,0.0],[0.0,0.0,0.0,0.1,0.0,0.0,0.9,0.0,0.0],[0.0,0.0,0.0,0.0,0.1,0.0,0.0,0.9,0.0],[0.0,0.0,0.0,0.0,0.0,0.1,0.0,0.0,0.9],[0.0,0.0,0.0,0.0,0.0,0.0,0.1,0.0,0.0],[0.0,0.0,0.0,0.0,0.0,0.0,0.0,0.1,0.0],[0.0,0.0,0.0,0.0,0.0,0.0,0.0,0.0,0.1]],[[0.1,0.0,0.0,0.0,0.0,0.0,0.0,0.0,0.0],[0.0,0.1,0.0,0.0,0.0,0.0,0.0,0.0,0.0],[0.0,0.0,0.1,0.0,0.0,0.0,0.0,0.0,0.0],[0.9,0.0,0.0,0.1,0.0,0.0,0.0,0.0,0.0],[0.0,0.9,0.0,0.0,0.1,0.0,0.0,0.0,0.0],[0.0,0.0,0.9,0.0,0.0,0.1,0.0,0.0,0.0],[0.0,0.0,0.0,0.9,0.0,0.0,1.0,0.0,0.0],[0.0,0.0,0.0,0.0,0.9,0.0,0.0,1.0,0.0],[0.0,0.0,0.0,0.0,0.0,0.9,0.0,0.0,1.0]],[[0.1,0.0,0.0,0.0,0.0,0.0,0.0,0.0,0.0],[0.9,0.1,0.0,0.0,0.0,0.0,0.0,0.0,0.0],[0.0,0.9,1.0,0.0,0.0,0.0,0.0,0.0,0.0],[0.0,0.0,0.0,0.1,0.0,0.0,0.0,0.0,0.0],[0.0,0.0,0.0,0.9,0.1,0.0,0.0,0.0,0.0],[0.0,0.0,0.0,0.0,0.9,1.0,0.0,0.0,0.0],[0.0,0.0,0.0,0.0,0.0,0.0,0.1,0.0,0.0],[0.0,0.0,0.0,0.0,0.0,0.0,0.9,0.1,0.0],[0.0,0.0,0.0,0.0,0.0,0.0,0.0,0.9,1.0]],[[1.0,0.9,0.0,0.0,0.0,0.0,0.0,0.0,0.0],[0.0,0.1,0.9,0.0,0.0,0.0,0.0,0.0,0.0],[0.0,0.0,0.1,0.0,0.0,0.0,0.0,0.0,0.0],[0.0,0.0,0.0,1.0,0.9,0.0,0.0,0.0,0.0],[0.0,0.0,0.0,0.0,0.1,0.9,0.0,0.0,0.0],[0.0,0.0,0.0,0.0,0.0,0.1,0.0,0.0,0.0],[0.0,0.0,0.0,0.0,0.0,0.0,1.0,0.9,0.0],[0.0,0.0,0.0,0.0,0.0,0.0,0.0,0.1,0.9],[0.0,0.0,0.0,0.0,0.0,0.0,0.0,0.0,0.1]]],"type_hint":null,"description":null},{"name":"B_agent3","value":[[[1.0,0.0,0.0,0.9,0.0,0.0,0.0,0.0,0.0],[0.0,1.0,0.0,0.0,0.9,0.0,0.0,0.0,0.0],[0.0,0.0,1.0,0.0,0.0,0.9,0.0,0.0,0.0],[0.0,0.0,0.0,0.1,0.0,0.0,0.9,0.0,0.0],[0.0,0.0,0.0,0.0,0.1,0.0,0.0,0.9,0.0],[0.0,0.0,0.0,0.0,0.0,0.1,0.0,0.0,0.9],[0.0,0.0,0.0,0.0,0.0,0.0,0.1,0.0,0.0],[0.0,0.0,0.0,0.0,0.0,0.0,0.0,0.1,0.0],[0.0,0.0,0.0,0.0,0.0,0.0,0.0,0.0,0.1]],[[0.1,0.0,0.0,0.0,0.0,0.0,0.0,0.0,0.0],[0.0,0.1,0.0,0.0,0.0,0.0,0.0,0.0,0.0],[0.0,0.0,0.1,0.0,0.0,0.0,0.0,0.0,0.0],[0.9,0.0,0.0,0.1,0.0,0.0,0.0,0.0,0.0],[0.0,0.9,0.0,0.0,0.1,0.0,0.0,0.0,0.0],[0.0,0.0,0.9,0.0,0.0,0.1,0.0,0.0,0.0],[0.0,0.0,0.0,0.9,0.0,0.0,1.0,0.0,0.0],[0.0,0.0,0.0,0.0,0.9,0.0,0.0,1.0,0.0],[0.0,0.0,0.0,0.0,0.0,0.9,0.0,0.0,1.0]],[[0.1,0.0,0.0,0.0,0.0,0.0,0.0,0.0,0.0],[0.9,0.1,0.0,0.0,0.0,0.0,0.0,0.0,0.0],[0.0,0.9,1.0,0.0,0.0,0.0,0.0,0.0,0.0],[0.0,0.0,0.0,0.1,0.0,0.0,0.0,0.0,0.0],[0.0,0.0,0.0,0.9,0.1,0.0,0.0,0.0,0.0],[0.0,0.0,0.0,0.0,0.9,1.0,0.0,0.0,0.0],[0.0,0.0,0.0,0.0,0.0,0.0,0.1,0.0,0.0],[0.0,0.0,0.0,0.0,0.0,0.0,0.9,0.1,0.0],[0.0,0.0,0.0,0.0,0.0,0.0,0.0,0.9,1.0]],[[1.0,0.9,0.0,0.0,0.0,0.0,0.0,0.0,0.0],[0.0,0.1,0.9,0.0,0.0,0.0,0.0,0.0,0.0],[0.0,0.0,0.1,0.0,0.0,0.0,0.0,0.0,0.0],[0.0,0.0,0.0,1.0,0.9,0.0,0.0,0.0,0.0],[0.0,0.0,0.0,0.0,0.1,0.9,0.0,0.0,0.0],[0.0,0.0,0.0,0.0,0.0,0.1,0.0,0.0,0.0],[0.0,0.0,0.0,0.0,0.0,0.0,1.0,0.9,0.0],[0.0,0.0,0.0,0.0,0.0,0.0,0.0,0.1,0.9],[0.0,0.0,0.0,0.0,0.0,0.0,0.0,0.0,0.1]]],"type_hint":null,"description":null},{"name":"env_signal","value":[[0.0,0.0,0.0,0.0,0.0,0.0,0.0,0.0,0.0]],"type_hint":null,"description":null},{"name":"signal_decay","value":[[0.9]],"type_hint":null,"description":null},{"name":"env_obs_likelihood","value":[[0.7,0.1,0.05],[0.15,0.7,0.15],[0.1,0.15,0.75],[0.05,0.05,0.05]],"type_hint":null,"description":null},{"name":"env_signal_prior","value":[[0.7,0.2,0.1]],"type_hint":null,"description":null},{"name":"signal_seek","value":[[2.0]],"type_hint":null,"description":null},{"name":"num_hidden_states","value":729,"type_hint":null,"description":null},{"name":"num_obs","value":64,"type_hint":null,"description":null},{"name":"num_actions","value":4,"type_hint":null,"description":null},{"name":"num_agents","value":3,"type_hint":null,"description":null},{"name":"grid_size","value":9,"type_hint":null,"description":null},{"name":"num_obs","value":4,"type_hint":null,"description":null},{"name":"num_actions","value":4,"type_hint":null,"description":null},{"name":"signal_decay_rate","value":0.9,"type_hint":null,"description":null},{"name":"signal_deposit_rate","value":0.3,"type_hint":null,"description":null},{"name":"num_timesteps","value":30,"type_hint":null,"description":null}],"equations":[],"time_specification":{"time_type":"Dynamic","discretization":null,"horizon":30,"step_size":null},"ontology_mappings":[{"variable_name":"A_agent1","ontology_term":"Agent1LikelihoodMatrix","description":null},{"variable_name":"C_agent1","ontology_term":"Agent1PreferenceVector","description":null},{"variable_name":"D_agent1","ontology_term":"Agent1PositionPrior","description":null},{"variable_name":"s_agent1","ontology_term":"Agent1PositionState","description":null},{"variable_name":"o_agent1","ontology_term":"Agent1Observation","description":null},{"variable_name":"pi1","ontology_term":"Agent1PolicyVector","description":null},{"variable_name":"u_agent1","ontology_term":"Agent1Action","description":null},{"variable_name":"G1","ontology_term":"Agent1ExpectedFreeEnergy","description":null},{"variable_name":"A_agent2","ontology_term":"Agent2LikelihoodMatrix","description":null},{"variable_name":"C_agent2","ontology_term":"Agent2PreferenceVector","description":null},{"variable_name":"D_agent2","ontology_term":"Agent2PositionPrior","description":null},{"variable_name":"s_agent2","ontology_term":"Agent2PositionState","description":null},{"variable_name":"o_agent2","ontology_term":"Agent2Observation","description":null},{"variable_name":"pi2","ontology_term":"Agent2PolicyVector","description":null},{"variable_name":"u_agent2","ontology_term":"Agent2Action","description":null},{"variable_name":"G2","ontology_term":"Agent2ExpectedFreeEnergy","description":null},{"variable_name":"A_agent3","ontology_term":"Agent3LikelihoodMatrix","description":null},{"variable_name":"C_agent3","ontology_term":"Agent3PreferenceVector","description":null},{"variable_name":"D_agent3","ontology_term":"Agent3PositionPrior","description":null},{"variable_name":"s_agent3","ontology_term":"Agent3PositionState","description":null},{"variable_name":"o_agent3","ontology_term":"Agent3Observation","description":null},{"variable_name":"pi3","ontology_term":"Agent3PolicyVector","description":null},{"variable_name":"u_agent3","ontology_term":"Agent3Action","description":null},{"variable_name":"G3","ontology_term":"Agent3ExpectedFreeEnergy","description":null},{"variable_name":"env_signal","ontology_term":"EnvironmentalSignal","description":null},{"variable_name":"signal_decay","ontology_term":"SignalDecayRate","description":null},{"variable_name":"t","ontology_term":"Time","description":null}]}
