TwoStateBistablePOMDP-Schema DEFINITIONS AUTOMATIC TAGS ::= BEGIN

-- GNN Model Schema Definition
-- Model: Two State Bistable POMDP
-- This model describes a minimal 2-state bistable POMDP:
-- 
-- - 2 hidden states: "left" and "right" in a symmetric bistable potential.
-- - 2 noisy observations: the agent gets a noisy readout of which side it is on.
-- - 2 actions: push-left or push-right.
-- - The agent prefers observation 1 ("right") over observation 0 ("left").
-- - Tests the absolute smallest POMDP with full active inference structure.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Two State Bistable POMDP",
    version "1.0",
    annotation "This model describes a minimal 2-state bistable POMDP:  - 2 hidden states: ""left"" and ""right"" in a symmetric bistable potential. - 2 noisy observations: the agent gets a noisy readout of which side it is on. - 2 actions: push-left or push-right. - The agent prefers observation 1 (""right"") over observation 0 (""left""). - Tests the absolute smallest POMDP with full active inference structure.",
    variables {
        {
            name "A",
            varType "likelihood_matrix",
            dataType "float"
            dimensions { 2, 2 }
        },
        {
            name "B",
            varType "transition_matrix",
            dataType "float"
            dimensions { 2, 2, 2 }
        },
        {
            name "C",
            varType "preference_vector",
            dataType "float"
            dimensions { 2 }
        }
    }
}

END -- TwoStateBistablePOMDP-Schema


-- MODEL_DATA: {"model_name":"Two State Bistable POMDP","version":"1.0","annotation":"This model describes a minimal 2-state bistable POMDP:\n\n- 2 hidden states: \"left\" and \"right\" in a symmetric bistable potential.\n- 2 noisy observations: the agent gets a noisy readout of which side it is on.\n- 2 actions: push-left or push-right.\n- The agent prefers observation 1 (\"right\") over observation 0 (\"left\").\n- Tests the absolute smallest POMDP with full active inference structure.","variables":[{"name":"A","var_type":"likelihood_matrix","data_type":"float","dimensions":[2,2],"description":"Noisy observation of state"},{"name":"B","var_type":"transition_matrix","data_type":"float","dimensions":[2,2,2],"description":"Action-dependent transitions"},{"name":"C","var_type":"preference_vector","data_type":"float","dimensions":[2],"description":"Prefer right side"},{"name":"D","var_type":"prior_vector","data_type":"float","dimensions":[2],"description":"Prior over initial states"},{"name":"E","var_type":"policy","data_type":"float","dimensions":[2],"description":"Prior over actions"},{"name":"s","var_type":"hidden_state","data_type":"float","dimensions":[2,1],"description":"Current state belief"},{"name":"s_prime","var_type":"hidden_state","data_type":"float","dimensions":[2,1],"description":"Next state belief"},{"name":"o","var_type":"observation","data_type":"integer","dimensions":[2,1],"description":"Current observation"},{"name":"\u03c0","var_type":"policy","data_type":"float","dimensions":[2],"description":"Policy over actions"},{"name":"u","var_type":"action","data_type":"integer","dimensions":[1],"description":"Chosen action"},{"name":"G","var_type":"policy","data_type":"float","dimensions":[1],"description":"Expected Free Energy"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["A"],"target_variables":["o"],"connection_type":"undirected","weight":null,"description":null},{"annotation":null,"source_variables":["s"],"target_variables":["s_prime"],"connection_type":"directed","weight":null,"description":null},{"annotation":null,"source_variables":["s"],"target_variables":["B"],"connection_type":"undirected","weight":null,"description":null},{"annotation":null,"source_variables":["C"],"target_variables":["G"],"connection_type":"directed","weight":null,"description":null},{"annotation":null,"source_variables":["E"],"target_variables":["\u03c0"],"connection_type":"directed","weight":null,"description":null},{"annotation":null,"source_variables":["G"],"target_variables":["\u03c0"],"connection_type":"directed","weight":null,"description":null},{"annotation":null,"source_variables":["\u03c0"],"target_variables":["u"],"connection_type":"directed","weight":null,"description":null},{"annotation":null,"source_variables":["B"],"target_variables":["u"],"connection_type":"directed","weight":null,"description":null},{"annotation":null,"source_variables":["u"],"target_variables":["s_prime"],"connection_type":"directed","weight":null,"description":null}],"parameters":[{"name":"A","value":[[0.8,0.2],[0.2,0.8]],"type_hint":null,"description":null},{"name":"B","value":[[[0.8,0.3],[0.2,0.7]],[[0.3,0.8],[0.7,0.2]]],"type_hint":null,"description":null},{"name":"C","value":[[0.0,2.0]],"type_hint":null,"description":null},{"name":"D","value":[[0.5,0.5]],"type_hint":null,"description":null},{"name":"E","value":[[0.5,0.5]],"type_hint":null,"description":null},{"name":"num_hidden_states","value":2,"type_hint":null,"description":null},{"name":"num_obs","value":2,"type_hint":null,"description":null},{"name":"num_actions","value":2,"type_hint":null,"description":null},{"name":"num_timesteps","value":20,"type_hint":null,"description":null}],"equations":[],"time_specification":{"time_type":"Dynamic","discretization":null,"horizon":"Unbounded","step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"E","ontology_term":"Habit","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"t","ontology_term":"Time","description":null}]}
