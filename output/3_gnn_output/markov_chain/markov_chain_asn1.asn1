SimpleMarkovChain-Schema DEFINITIONS AUTOMATIC TAGS ::= BEGIN

-- GNN Model Schema Definition
-- Model: Simple Markov Chain
-- This model describes a minimal discrete-time Markov Chain:
-- 
-- - 3 states representing weather (sunny, cloudy, rainy).
-- - No actions — the system evolves passively.
-- - Observations = states directly (identity mapping for monitoring).
-- - Stationary transition matrix with realistic weather dynamics.
-- - Tests the simplest model structure: passive state evolution with no control.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Simple Markov Chain",
    version "1.0",
    annotation "This model describes a minimal discrete-time Markov Chain:  - 3 states representing weather (sunny, cloudy, rainy). - No actions — the system evolves passively. - Observations = states directly (identity mapping for monitoring). - Stationary transition matrix with realistic weather dynamics. - Tests the simplest model structure: passive state evolution with no control.",
    variables {
        {
            name "A",
            varType "likelihood_matrix",
            dataType "float"
            dimensions { 3, 3 }
        },
        {
            name "B",
            varType "transition_matrix",
            dataType "float"
            dimensions { 3, 3 }
        },
        {
            name "D",
            varType "prior_vector",
            dataType "float"
            dimensions { 3 }
        }
    }
}

END -- SimpleMarkovChain-Schema


-- MODEL_DATA: {"model_name":"Simple Markov Chain","version":"1.0","annotation":"This model describes a minimal discrete-time Markov Chain:\n\n- 3 states representing weather (sunny, cloudy, rainy).\n- No actions \u2014 the system evolves passively.\n- Observations = states directly (identity mapping for monitoring).\n- Stationary transition matrix with realistic weather dynamics.\n- Tests the simplest model structure: passive state evolution with no control.","variables":[{"name":"A","var_type":"likelihood_matrix","data_type":"float","dimensions":[3,3],"description":"Observation model (identity for direct monitoring)"},{"name":"B","var_type":"transition_matrix","data_type":"float","dimensions":[3,3],"description":"Markov transition matrix"},{"name":"D","var_type":"prior_vector","data_type":"float","dimensions":[3],"description":"Prior over initial states"},{"name":"s","var_type":"hidden_state","data_type":"float","dimensions":[3,1],"description":"Current state distribution"},{"name":"s_prime","var_type":"hidden_state","data_type":"float","dimensions":[3,1],"description":"Next state distribution"},{"name":"o","var_type":"observation","data_type":"integer","dimensions":[3,1],"description":"Current observation"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["A"],"target_variables":["o"],"connection_type":"undirected","weight":null,"description":null},{"annotation":null,"source_variables":["s"],"target_variables":["s_prime"],"connection_type":"directed","weight":null,"description":null},{"annotation":null,"source_variables":["B"],"target_variables":["s_prime"],"connection_type":"directed","weight":null,"description":null},{"annotation":null,"source_variables":["s"],"target_variables":["B"],"connection_type":"undirected","weight":null,"description":null}],"parameters":[{"name":"A","value":[[1.0,0.0,0.0],[0.0,1.0,0.0],[0.0,0.0,1.0]],"type_hint":null,"description":null},{"name":"B","value":[[0.7,0.3,0.1],[0.2,0.4,0.3],[0.1,0.3,0.6]],"type_hint":null,"description":null},{"name":"D","value":[[0.5,0.3,0.2]],"type_hint":null,"description":null},{"name":"num_hidden_states","value":3,"type_hint":null,"description":null},{"name":"num_obs","value":3,"type_hint":null,"description":null},{"name":"num_actions","value":1,"type_hint":null,"description":null},{"name":"num_timesteps","value":40,"type_hint":null,"description":null}],"equations":[],"time_specification":{"time_type":"Dynamic","discretization":null,"horizon":"Unbounded","step_size":null},"ontology_mappings":[{"variable_name":"A","ontology_term":"EmissionMatrix","description":null},{"variable_name":"B","ontology_term":"TransitionMatrix","description":null},{"variable_name":"D","ontology_term":"InitialStateDistribution","description":null},{"variable_name":"s","ontology_term":"HiddenState","description":null},{"variable_name":"s_prime","ontology_term":"NextHiddenState","description":null},{"variable_name":"o","ontology_term":"Observation","description":null},{"variable_name":"t","ontology_term":"Time","description":null}]}
