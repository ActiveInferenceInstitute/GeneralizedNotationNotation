Time-VaryingTransitionDynamicsAgent-Schema DEFINITIONS AUTOMATIC TAGS ::= BEGIN

-- GNN Model Schema Definition
-- Model: Time-Varying Transition Dynamics Agent
-- A POMDP agent operating in a non-stationary environment. The key feature
-- is that the transition matrix `B` is indexed by time (`B_t`), capturing
-- dynamics that evolve across the planning horizon — e.g., shifting wind
-- patterns for a sailing agent, or changing opponent strategy in a
-- sequential game.
-- 
-- - 3 hidden states, 3 observations, 2 actions
-- - B_t: 3D transition tensor per timestep (shape: next_state × current_state × action)
-- - Agent must adapt belief updates each step to the current B_t
-- - Exercises time-varying matrix handling in renderers
-- 
-- This sample pushes the language extensions around time-indexed tensors
-- and tests downstream code generation when matrix literals are
-- timestep-dependent.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Time-Varying Transition Dynamics Agent",
    version "1.0",
    annotation "A POMDP agent operating in a non-stationary environment. The key feature is that the transition matrix `B` is indexed by time (`B_t`), capturing dynamics that evolve across the planning horizon — e.g., shifting wind patterns for a sailing agent, or changing opponent strategy in a sequential game.  - 3 hidden states, 3 observations, 2 actions - B_t: 3D transition tensor per timestep (shape: next_state × current_state × action) - Agent must adapt belief updates each step to the current B_t - Exercises time-varying matrix handling in renderers  This sample pushes the language extensions around time-indexed tensors and tests downstream code generation when matrix literals are timestep-dependent.",
    variables {
        {
            name "A",
            varType "likelihood_matrix",
            dataType "float"
            dimensions { 3, 3 }
        },
        {
            name "B_t",
            varType "hidden_state",
            dataType "float"
            dimensions { 3, 3, 2 }
        },
        {
            name "C",
            varType "preference_vector",
            dataType "float"
            dimensions { 3, 1 }
        }
    }
}

END -- Time-VaryingTransitionDynamicsAgent-Schema


-- MODEL_DATA: {"model_name":"Time-Varying Transition Dynamics Agent","version":"1.0","annotation":"A POMDP agent operating in a non-stationary environment. The key feature\nis that the transition matrix `B` is indexed by time (`B_t`), capturing\ndynamics that evolve across the planning horizon \u2014 e.g., shifting wind\npatterns for a sailing agent, or changing opponent strategy in a\nsequential game.\n\n- 3 hidden states, 3 observations, 2 actions\n- B_t: 3D transition tensor per timestep (shape: next_state \u00d7 current_state \u00d7 action)\n- Agent must adapt belief updates each step to the current B_t\n- Exercises time-varying matrix handling in renderers\n\nThis sample pushes the language extensions around time-indexed tensors\nand tests downstream code generation when matrix literals are\ntimestep-dependent.","variables":[{"name":"A","var_type":"likelihood_matrix","data_type":"float","dimensions":[3,3],"description":"Observation model (time-invariant)"},{"name":"B_t","var_type":"hidden_state","data_type":"float","dimensions":[3,3,2],"description":"Transition model, indexed by time t"},{"name":"C","var_type":"preference_vector","data_type":"float","dimensions":[3,1],"description":"Preference vector"},{"name":"D","var_type":"prior_vector","data_type":"float","dimensions":[3,1],"description":"Initial state prior"},{"name":"s_t","var_type":"hidden_state","data_type":"float","dimensions":[3,1],"description":"Hidden state at time t"},{"name":"s_t+1","var_type":"hidden_state","data_type":"float","dimensions":[3,1],"description":"Hidden state at time t+1"},{"name":"o_t","var_type":"observation","data_type":"integer","dimensions":[3,1],"description":"Observation at time t"},{"name":"u_t","var_type":"action","data_type":"integer","dimensions":[2,1],"description":"Action at time t"}],"connections":[{"annotation":null,"source_variables":["D"],"target_variables":["s_t"],"connection_type":"directed","weight":null,"description":null},{"annotation":null,"source_variables":["s_t","u_t"],"target_variables":["B_t"],"connection_type":"directed","weight":null,"description":null},{"annotation":null,"source_variables":["B_t"],"target_variables":["s_t+1"],"connection_type":"directed","weight":null,"description":null},{"annotation":null,"source_variables":["s_t"],"target_variables":["A"],"connection_type":"undirected","weight":null,"description":null},{"annotation":null,"source_variables":["A"],"target_variables":["o_t"],"connection_type":"undirected","weight":null,"description":null},{"annotation":null,"source_variables":["C"],"target_variables":["o_t"],"connection_type":"undirected","weight":null,"description":null}],"parameters":[{"name":"A","value":[[0.85,0.1,0.05],[0.1,0.8,0.1],[0.05,0.1,0.85]],"type_hint":null,"description":null},{"name":"B_t","value":[[[0.6,0.1],[0.3,0.1],[0.1,0.8]],[[0.3,0.1],[0.6,0.6],[0.1,0.3]],[[0.1,0.8],[0.1,0.3],[0.8,0.1]]],"type_hint":null,"description":null},{"name":"C","value":[[0.0,0.0,1.0]],"type_hint":null,"description":null},{"name":"D","value":[[0.33,0.33,0.34]],"type_hint":null,"description":null},{"name":"num_hidden_states","value":3,"type_hint":null,"description":null},{"name":"num_obs","value":3,"type_hint":null,"description":null},{"name":"num_actions","value":2,"type_hint":null,"description":null},{"name":"num_timesteps","value":10,"type_hint":null,"description":null}],"equations":[],"time_specification":{"time_type":"Dynamic","discretization":"DiscreteTime","horizon":10,"step_size":null},"ontology_mappings":[{"variable_name":"A","ontology_term":"LikelihoodMatrix","description":null},{"variable_name":"B_t","ontology_term":"TimeVaryingTransitionMatrix","description":null},{"variable_name":"C","ontology_term":"PreferenceVector","description":null},{"variable_name":"D","ontology_term":"Prior","description":null},{"variable_name":"s_t","ontology_term":"HiddenState","description":null},{"variable_name":"o_t","ontology_term":"Observation","description":null},{"variable_name":"u_t","ontology_term":"Action","description":null}]}
