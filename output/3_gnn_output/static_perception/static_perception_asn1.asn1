StaticPerceptionModel-Schema DEFINITIONS AUTOMATIC TAGS ::= BEGIN

-- GNN Model Schema Definition
-- Model: Static Perception Model
-- The simplest Active Inference model demonstrating pure perception:
-- 
-- - 2 hidden states mapped to 2 observations via a recognition matrix A
-- - Prior D encodes initial beliefs over hidden states
-- - Minimal 2-action transition component B so the model is a complete POMDP
--   (renderable and executable by pymdp and the general simulation frameworks)
-- - Suitable as a minimal baseline and for testing perception-only inference

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Static Perception Model",
    version "1.0",
    annotation "The simplest Active Inference model demonstrating pure perception:  - 2 hidden states mapped to 2 observations via a recognition matrix A - Prior D encodes initial beliefs over hidden states - Minimal 2-action transition component B so the model is a complete POMDP   (renderable and executable by pymdp and the general simulation frameworks) - Suitable as a minimal baseline and for testing perception-only inference",
    variables {
        {
            name "A",
            varType "likelihood_matrix",
            dataType "float"
            dimensions { 2, 2 }
        },
        {
            name "B",
            varType "transition_matrix",
            dataType "float"
            dimensions { 2, 2, 2 }
        },
        {
            name "C",
            varType "preference_vector",
            dataType "float"
            dimensions { 2 }
        }
    }
}

END -- StaticPerceptionModel-Schema


-- MODEL_DATA: {"model_name":"Static Perception Model","version":"1.0","annotation":"The simplest Active Inference model demonstrating pure perception:\n\n- 2 hidden states mapped to 2 observations via a recognition matrix A\n- Prior D encodes initial beliefs over hidden states\n- Minimal 2-action transition component B so the model is a complete POMDP\n  (renderable and executable by pymdp and the general simulation frameworks)\n- Suitable as a minimal baseline and for testing perception-only inference","variables":[{"name":"A","var_type":"likelihood_matrix","data_type":"float","dimensions":[2,2],"description":"Recognition/likelihood matrix: P(observation | hidden state)"},{"name":"B","var_type":"transition_matrix","data_type":"float","dimensions":[2,2,2],"description":"Transition matrix: B[next_state, previous_state, actions]"},{"name":"C","var_type":"preference_vector","data_type":"float","dimensions":[2],"description":"Preference vector over observations"},{"name":"D","var_type":"prior_vector","data_type":"float","dimensions":[2,1],"description":"Prior belief over hidden states"},{"name":"s","var_type":"hidden_state","data_type":"float","dimensions":[2,1],"description":"Hidden state (posterior belief)"},{"name":"o","var_type":"observation","data_type":"integer","dimensions":[2,1],"description":"Observation (one-hot encoded)"},{"name":"u","var_type":"action","data_type":"integer","dimensions":[1],"description":"Action taken"}],"connections":[{"annotation":null,"source_variables":["D"],"target_variables":["s"],"connection_type":"directed","weight":null,"description":null},{"annotation":null,"source_variables":["s"],"target_variables":["A"],"connection_type":"undirected","weight":null,"description":null},{"annotation":null,"source_variables":["A"],"target_variables":["o"],"connection_type":"undirected","weight":null,"description":null},{"annotation":null,"source_variables":["s"],"target_variables":["B"],"connection_type":"undirected","weight":null,"description":null},{"annotation":null,"source_variables":["B"],"target_variables":["u"],"connection_type":"directed","weight":null,"description":null},{"annotation":null,"source_variables":["u"],"target_variables":["s"],"connection_type":"directed","weight":null,"description":null}],"parameters":[{"name":"A","value":[[0.9,0.1],[0.2,0.8]],"type_hint":null,"description":null},{"name":"B","value":[[[0.95,0.05],[0.05,0.95]],[[0.05,0.95],[0.95,0.05]]],"type_hint":null,"description":null},{"name":"C","value":[[0.0,0.0]],"type_hint":null,"description":null},{"name":"D","value":[[0.5,0.5]],"type_hint":null,"description":null},{"name":"num_hidden_states","value":2,"type_hint":null,"description":null},{"name":"num_obs","value":2,"type_hint":null,"description":null},{"name":"num_actions","value":2,"type_hint":null,"description":null},{"name":"num_timesteps","value":5,"type_hint":null,"description":null}],"equations":[],"time_specification":{"time_type":"Static","discretization":null,"horizon":null,"step_size":null},"ontology_mappings":[{"variable_name":"A","ontology_term":"RecognitionMatrix","description":null},{"variable_name":"B","ontology_term":"TransitionMatrix","description":null},{"variable_name":"C","ontology_term":"PreferenceVector","description":null},{"variable_name":"D","ontology_term":"Prior","description":null},{"variable_name":"s","ontology_term":"HiddenState","description":null},{"variable_name":"o","ontology_term":"Observation","description":null},{"variable_name":"u","ontology_term":"Action","description":null}]}
