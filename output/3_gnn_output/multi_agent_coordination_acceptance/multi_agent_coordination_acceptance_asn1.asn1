Multi-AgentCoordinationAcceptanceFixture-Schema DEFINITIONS AUTOMATIC TAGS ::= BEGIN

-- GNN Model Schema Definition
-- Model: Multi-Agent Coordination Acceptance Fixture
-- Compact fixture for RxInfer and DisCoPy roadmap acceptance tests.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Multi-Agent Coordination Acceptance Fixture",
    version "1.0",
    annotation "Compact fixture for RxInfer and DisCoPy roadmap acceptance tests.",
    variables {
        {
            name "s",
            varType "hidden_state",
            dataType "categorical"
            dimensions { 2, 1 }
        },
        {
            name "o",
            varType "observation",
            dataType "categorical"
            dimensions { 2, 1 }
        },
        {
            name "u",
            varType "action",
            dataType "categorical"
            dimensions { 2, 1 }
        }
    }
}

END -- Multi-AgentCoordinationAcceptanceFixture-Schema


-- MODEL_DATA: {"model_name":"Multi-Agent Coordination Acceptance Fixture","version":"1.0","annotation":"Compact fixture for RxInfer and DisCoPy roadmap acceptance tests.","variables":[{"name":"s","var_type":"hidden_state","data_type":"categorical","dimensions":[2,1],"description":null},{"name":"o","var_type":"observation","data_type":"categorical","dimensions":[2,1],"description":null},{"name":"u","var_type":"action","data_type":"categorical","dimensions":[2,1],"description":null}],"connections":[{"annotation":null,"source_variables":["s"],"target_variables":["o"],"connection_type":"directed","weight":null,"description":null},{"annotation":null,"source_variables":["s"],"target_variables":["s"],"connection_type":"directed","weight":null,"description":null},{"annotation":null,"source_variables":["u"],"target_variables":["s"],"connection_type":"directed","weight":null,"description":null}],"parameters":[{"name":"nr_agents","value":3,"type_hint":null,"description":null},{"name":"agent_ids","value":[1,2,3],"type_hint":null,"description":null},{"name":"agent_initial_positions","value":[[0.0,0.0],[1.0,0.0],[0.0,1.0]],"type_hint":null,"description":null},{"name":"agent_target_positions","value":[[2.0,2.0],[3.0,2.0],[2.0,3.0]],"type_hint":null,"description":null},{"name":"agent_radii","value":[1.0,1.0,1.0],"type_hint":null,"description":null},{"name":"agent_edges","value":[[1,2],[2,3]],"type_hint":null,"description":null},{"name":"agent_clusters","value":[{"name":"left","agent_ids":[1,2]},{"name":"right","agent_ids":[3]}],"type_hint":null,"description":null},{"name":"message_passing","value":"clustered_mean_field","type_hint":null,"description":null},{"name":"A","value":[[0.9,0.1],[0.1,0.9]],"type_hint":null,"description":null},{"name":"B","value":[[[0.9,0.1],[0.1,0.9]],[[0.1,0.9],[0.9,0.1]]],"type_hint":null,"description":null},{"name":"C","value":[[1.0,0.0]],"type_hint":null,"description":null},{"name":"D","value":[[0.5,0.5]],"type_hint":null,"description":null}],"equations":[],"time_specification":{"time_type":"Dynamic","discretization":null,"horizon":null,"step_size":null},"ontology_mappings":[{"variable_name":"s","ontology_term":"HiddenState","description":null},{"variable_name":"o","ontology_term":"Observation","description":null},{"variable_name":"u","ontology_term":"Action","description":null}]}
