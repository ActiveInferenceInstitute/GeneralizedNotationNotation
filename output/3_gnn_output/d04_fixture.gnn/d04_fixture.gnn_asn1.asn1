NESTD04Synthetic2-StateLGSSM-Schema DEFINITIONS AUTOMATIC TAGS ::= BEGIN

-- GNN Model Schema Definition
-- Model: NEST D04 Synthetic 2-State LGSSM
-- Passive linear-Gaussian state-space model (no control input) generating the
-- summary indices of the D02 MESSAGEix wrapper blanket over T coupling iterations.
-- - Hidden state x = (decarb_rate_dev, demand_pressure), dimensionless deviations.
-- - Observation y = (emissions_index, price_index, objective_index, demand_index): relative indices of total
--   emissions e, mean commodity price p, objective J and mean demand d against
--   fixed reference values (see the fixture JSON, `blanket.references`).
-- - cap (emissions cap) is a declared exogenous schedule in the fixture, not a
--   variable of this model.
-- Deliverable D04 (AII); pattern for D07 (3–5 states) and D14 (GNN → RxInfer render).

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "NEST D04 Synthetic 2-State LGSSM",
    version "1.0",
    annotation "Passive linear-Gaussian state-space model (no control input) generating the summary indices of the D02 MESSAGEix wrapper blanket over T coupling iterations. - Hidden state x = (decarb_rate_dev, demand_pressure), dimensionless deviations. - Observation y = (emissions_index, price_index, objective_index, demand_index): relative indices of total   emissions e, mean commodity price p, objective J and mean demand d against   fixed reference values (see the fixture JSON, `blanket.references`). - cap (emissions cap) is a declared exogenous schedule in the fixture, not a   variable of this model. Deliverable D04 (AII); pattern for D07 (3–5 states) and D14 (GNN → RxInfer render).",
    variables {
        {
            name "x",
            varType "hidden_state",
            dataType "float"
            dimensions { 2, 1 }
        },
        {
            name "y",
            varType "hidden_state",
            dataType "float"
            dimensions { 4, 1 }
        },
        {
            name "F",
            varType "hidden_state",
            dataType "float"
            dimensions { 2, 2 }
        }
    }
}

END -- NESTD04Synthetic2-StateLGSSM-Schema


-- MODEL_DATA: {"model_name":"NEST D04 Synthetic 2-State LGSSM","version":"1.0","annotation":"Passive linear-Gaussian state-space model (no control input) generating the\nsummary indices of the D02 MESSAGEix wrapper blanket over T coupling iterations.\n- Hidden state x = (decarb_rate_dev, demand_pressure), dimensionless deviations.\n- Observation y = (emissions_index, price_index, objective_index, demand_index): relative indices of total\n  emissions e, mean commodity price p, objective J and mean demand d against\n  fixed reference values (see the fixture JSON, `blanket.references`).\n- cap (emissions cap) is a declared exogenous schedule in the fixture, not a\n  variable of this model.\nDeliverable D04 (AII); pattern for D07 (3\u20135 states) and D14 (GNN \u2192 RxInfer render).","variables":[{"name":"x","var_type":"hidden_state","data_type":"float","dimensions":[2,1],"description":"hidden state (decarb_rate_dev, demand_pressure)"},{"name":"y","var_type":"hidden_state","data_type":"float","dimensions":[4,1],"description":"blanket summary indices"},{"name":"F","var_type":"hidden_state","data_type":"float","dimensions":[2,2],"description":"state transition"},{"name":"H","var_type":"hidden_state","data_type":"float","dimensions":[4,2],"description":"observation matrix"},{"name":"Q","var_type":"hidden_state","data_type":"float","dimensions":[2,2],"description":"process-noise covariance"},{"name":"R","var_type":"hidden_state","data_type":"float","dimensions":[4,4],"description":"observation-noise covariance"},{"name":"prior_mean","var_type":"prior_vector","data_type":"float","dimensions":[2],"description":"prior mean over x_1"},{"name":"prior_cov","var_type":"prior_vector","data_type":"float","dimensions":[2,2],"description":"prior covariance over x_1"},{"name":"t","var_type":"hidden_state","data_type":"integer","dimensions":[1],"description":"coupling iteration"}],"connections":[{"source_variables":["prior_mean"],"target_variables":["x"],"connection_type":"directed","weight":null,"description":null},{"source_variables":["F"],"target_variables":["x"],"connection_type":"directed","weight":null,"description":null},{"source_variables":["x"],"target_variables":["y"],"connection_type":"directed","weight":null,"description":null},{"source_variables":["H"],"target_variables":["y"],"connection_type":"directed","weight":null,"description":null},{"source_variables":["Q"],"target_variables":["x"],"connection_type":"directed","weight":null,"description":null},{"source_variables":["R"],"target_variables":["y"],"connection_type":"directed","weight":null,"description":null}],"parameters":[{"name":"F","value":[[0.85,-0.1],[0.05,0.9]],"type_hint":null,"description":null},{"name":"H","value":[[-0.8,0.5],[0.6,0.4],[0.3,0.7],[0.0,1.0]],"type_hint":null,"description":null},{"name":"Q","value":[[0.004,0.0005],[0.0005,0.006]],"type_hint":null,"description":null},{"name":"R","value":[[0.0025,0.0,0.0,0.0],[0.0,0.0036,0.0,0.0],[0.0,0.0,0.0016,0.0],[0.0,0.0,0.0,0.0009]],"type_hint":null,"description":null},{"name":"prior_mean","value":[[0.05,0.0]],"type_hint":null,"description":null},{"name":"prior_cov","value":[[0.02,0.0],[0.0,0.02]],"type_hint":null,"description":null},{"name":"num_timesteps","value":24,"type_hint":null,"description":null},{"name":"random_seed","value":20260910,"type_hint":null,"description":null},{"name":"num_states","value":2,"type_hint":null,"description":null},{"name":"num_observations","value":4,"type_hint":null,"description":null},{"name":"num_regions","value":1,"type_hint":null,"description":null},{"name":"num_commodities","value":2,"type_hint":null,"description":null},{"name":"num_time_slices","value":12,"type_hint":null,"description":null}],"equations":[],"time_specification":{"time_type":"Dynamic","discretization":null,"horizon":24,"step_size":null},"ontology_mappings":[{"variable_name":"F","ontology_term":"StateTransitionMatrix","description":null},{"variable_name":"H","ontology_term":"ObservationMatrix","description":null},{"variable_name":"Q","ontology_term":"ProcessNoiseCovariance","description":null},{"variable_name":"R","ontology_term":"ObservationNoiseCovariance","description":null},{"variable_name":"prior_mean","ontology_term":"PriorMean","description":null},{"variable_name":"prior_cov","ontology_term":"PriorCovariance","description":null},{"variable_name":"x","ontology_term":"ContinuousHiddenState","description":null},{"variable_name":"y","ontology_term":"ContinuousObservation","description":null},{"variable_name":"t","ontology_term":"Time","description":null}]}
