DirichletLikelihoodLearningAgent-Schema DEFINITIONS AUTOMATIC TAGS ::= BEGIN

-- GNN Model Schema Definition
-- Model: Dirichlet Likelihood Learning Agent
-- This model describes a discrete POMDP agent that learns its observation model:
-- 
-- - 3 hidden states, 3 observation outcomes, 2 actions (cycle, stay).
-- - The likelihood matrix A is NOT fixed: it is a latent DirichletCollection
--   variable with prior pseudo-counts declared in dirichlet_A.
-- - The A values under InitialParameterization are the GROUND-TRUTH likelihood
--   used by the environment to simulate observations; the agent never sees them
--   directly and must recover them in q(A).
-- - The Dirichlet prior is identity-biased (diagonal 3.0, off-diagonal 1.0):
--   the agent starts believing observations weakly track states. A fully
--   uniform prior leaves the column-permutation symmetry unbroken and
--   variational inference converges to a label-switched optimum.
-- - Transitions B are near-deterministic and known, so states are
--   well-determined by actions and likelihood learning is well-conditioned.
-- - Inference: structured VMP with mean-field cut q(s, A) = q(s)q(A),
--   q(A) initialized at the prior counts, q(s) initialized uniform.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Dirichlet Likelihood Learning Agent",
    version "1.0",
    annotation "This model describes a discrete POMDP agent that learns its observation model:  - 3 hidden states, 3 observation outcomes, 2 actions (cycle, stay). - The likelihood matrix A is NOT fixed: it is a latent DirichletCollection   variable with prior pseudo-counts declared in dirichlet_A. - The A values under InitialParameterization are the GROUND-TRUTH likelihood   used by the environment to simulate observations; the agent never sees them   directly and must recover them in q(A). - The Dirichlet prior is identity-biased (diagonal 3.0, off-diagonal 1.0):   the agent starts believing observations weakly track states. A fully   uniform prior leaves the column-permutation symmetry unbroken and   variational inference converges to a label-switched optimum. - Transitions B are near-deterministic and known, so states are   well-determined by actions and likelihood learning is well-conditioned. - Inference: structured VMP with mean-field cut q(s, A) = q(s)q(A),   q(A) initialized at the prior counts, q(s) initialized uniform.",
    variables {
        {
            name "A",
            varType "likelihood_matrix",
            dataType "float"
            dimensions { 3, 3 }
        },
        {
            name "B",
            varType "transition_matrix",
            dataType "float"
            dimensions { 3, 3, 2 }
        },
        {
            name "C",
            varType "preference_vector",
            dataType "float"
            dimensions { 3 }
        }
    }
}

END -- DirichletLikelihoodLearningAgent-Schema


-- MODEL_DATA: {"model_name":"Dirichlet Likelihood Learning Agent","version":"1.0","annotation":"This model describes a discrete POMDP agent that learns its observation model:\n\n- 3 hidden states, 3 observation outcomes, 2 actions (cycle, stay).\n- The likelihood matrix A is NOT fixed: it is a latent DirichletCollection\n  variable with prior pseudo-counts declared in dirichlet_A.\n- The A values under InitialParameterization are the GROUND-TRUTH likelihood\n  used by the environment to simulate observations; the agent never sees them\n  directly and must recover them in q(A).\n- The Dirichlet prior is identity-biased (diagonal 3.0, off-diagonal 1.0):\n  the agent starts believing observations weakly track states. A fully\n  uniform prior leaves the column-permutation symmetry unbroken and\n  variational inference converges to a label-switched optimum.\n- Transitions B are near-deterministic and known, so states are\n  well-determined by actions and likelihood learning is well-conditioned.\n- Inference: structured VMP with mean-field cut q(s, A) = q(s)q(A),\n  q(A) initialized at the prior counts, q(s) initialized uniform.","variables":[{"name":"A","var_type":"likelihood_matrix","data_type":"float","dimensions":[3,3],"description":"Ground-truth observation model P(o|s); latent in the agent"},{"name":"B","var_type":"transition_matrix","data_type":"float","dimensions":[3,3,2],"description":"State transitions given previous state and action"},{"name":"C","var_type":"preference_vector","data_type":"float","dimensions":[3],"description":"Log-preferences over observations"},{"name":"D","var_type":"prior_vector","data_type":"float","dimensions":[3],"description":"Prior over initial hidden states (known start)"},{"name":"dirichlet_A","var_type":"hidden_state","data_type":"float","dimensions":[3,3],"description":"Prior counts for q(A) ~ DirichletCollection"},{"name":"s","var_type":"hidden_state","data_type":"float","dimensions":[3,1],"description":"Current hidden state distribution"},{"name":"s_prime","var_type":"hidden_state","data_type":"float","dimensions":[3,1],"description":"Next hidden state distribution"},{"name":"o","var_type":"observation","data_type":"integer","dimensions":[3,1],"description":"Current observation index"},{"name":"\u03c0","var_type":"policy","data_type":"float","dimensions":[2],"description":"Policy (distribution over actions)"},{"name":"u","var_type":"action","data_type":"integer","dimensions":[1],"description":"Action taken"},{"name":"G","var_type":"policy","data_type":"float","dimensions":[1],"description":"Expected Free Energy (per policy)"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["s"],"target_variables":["s_prime"],"connection_type":"directed","weight":null,"description":null},{"annotation":null,"source_variables":["A"],"target_variables":["o"],"connection_type":"undirected","weight":null,"description":null},{"annotation":null,"source_variables":["s"],"target_variables":["B"],"connection_type":"undirected","weight":null,"description":null},{"annotation":null,"source_variables":["C"],"target_variables":["G"],"connection_type":"directed","weight":null,"description":null},{"annotation":null,"source_variables":["G"],"target_variables":["\u03c0"],"connection_type":"directed","weight":null,"description":null},{"annotation":null,"source_variables":["\u03c0"],"target_variables":["u"],"connection_type":"directed","weight":null,"description":null},{"annotation":null,"source_variables":["B"],"target_variables":["u"],"connection_type":"directed","weight":null,"description":null},{"annotation":null,"source_variables":["u"],"target_variables":["s_prime"],"connection_type":"directed","weight":null,"description":null}],"parameters":[{"name":"A","value":[[0.85,0.05,0.1],[0.1,0.9,0.05],[0.05,0.05,0.85]],"type_hint":null,"description":null},{"name":"B","value":[[[0.1,0.9],[0.0,0.05],[0.9,0.05]],[[0.9,0.05],[0.1,0.9],[0.0,0.05]],[[0.0,0.05],[0.9,0.05],[0.1,0.9]]],"type_hint":null,"description":null},{"name":"C","value":[[0.0,0.0,1.0]],"type_hint":null,"description":null},{"name":"D","value":[[1.0,0.0,0.0]],"type_hint":null,"description":null},{"name":"dirichlet_A","value":[[3.0,1.0,1.0],[1.0,3.0,1.0],[1.0,1.0,3.0]],"type_hint":null,"description":null},{"name":"num_hidden_states","value":3,"type_hint":null,"description":null},{"name":"num_obs","value":3,"type_hint":null,"description":null},{"name":"num_actions","value":2,"type_hint":null,"description":null},{"name":"num_timesteps","value":15,"type_hint":null,"description":null},{"name":"inference_iterations","value":40,"type_hint":null,"description":null}],"equations":[],"time_specification":{"time_type":"Dynamic","discretization":null,"horizon":"Unbounded","step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"dirichlet_A","ontology_term":"LikelihoodMatrixConcentrationParameters","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"t","ontology_term":"Time","description":null}]}
