ContinuousStateNavigationAgent-Schema DEFINITIONS AUTOMATIC TAGS ::= BEGIN

-- GNN Model Schema Definition
-- Model: Continuous State Navigation Agent
-- A continuous-state Active Inference navigation agent rendered as a native
-- linear-Gaussian state-space model (LGSSM):
-- - Hidden state x = (x, y): the continuous 2D position of the navigator.
-- - Observation y: noisy readings of the 2D position (identity readout).
-- - Control input u: a goal-seeking command added to the state each step.
-- - The controller closes the loop on beliefs — it pushes the filtered posterior
--   mean toward the preferred position goal_mean = (2.0, 2.0) with proportional
--   gain control_gain = 0.3, i.e. u_t = control_gain * (goal_mean - mu_t).

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Continuous State Navigation Agent",
    version "1.0",
    annotation "A continuous-state Active Inference navigation agent rendered as a native linear-Gaussian state-space model (LGSSM): - Hidden state x = (x, y): the continuous 2D position of the navigator. - Observation y: noisy readings of the 2D position (identity readout). - Control input u: a goal-seeking command added to the state each step. - The controller closes the loop on beliefs — it pushes the filtered posterior   mean toward the preferred position goal_mean = (2.0, 2.0) with proportional   gain control_gain = 0.3, i.e. u_t = control_gain * (goal_mean - mu_t).",
    variables {
        {
            name "x",
            varType "hidden_state",
            dataType "float"
            dimensions { 2, 1 }
        },
        {
            name "y",
            varType "hidden_state",
            dataType "float"
            dimensions { 2, 1 }
        },
        {
            name "u",
            varType "action",
            dataType "float"
            dimensions { 2, 1 }
        }
    }
}

END -- ContinuousStateNavigationAgent-Schema


-- MODEL_DATA: {"model_name":"Continuous State Navigation Agent","version":"1.0","annotation":"A continuous-state Active Inference navigation agent rendered as a native\nlinear-Gaussian state-space model (LGSSM):\n- Hidden state x = (x, y): the continuous 2D position of the navigator.\n- Observation y: noisy readings of the 2D position (identity readout).\n- Control input u: a goal-seeking command added to the state each step.\n- The controller closes the loop on beliefs \u2014 it pushes the filtered posterior\n  mean toward the preferred position goal_mean = (2.0, 2.0) with proportional\n  gain control_gain = 0.3, i.e. u_t = control_gain * (goal_mean - mu_t).","variables":[{"name":"x","var_type":"hidden_state","data_type":"float","dimensions":[2,1],"description":"continuous latent state"},{"name":"y","var_type":"hidden_state","data_type":"float","dimensions":[2,1],"description":"continuous observation"},{"name":"u","var_type":"action","data_type":"float","dimensions":[2,1],"description":"control input"},{"name":"F","var_type":"hidden_state","data_type":"float","dimensions":[2,2],"description":"state transition"},{"name":"H","var_type":"hidden_state","data_type":"float","dimensions":[2,2],"description":"observation matrix"},{"name":"Q","var_type":"hidden_state","data_type":"float","dimensions":[2,2],"description":"process-noise covariance"},{"name":"R","var_type":"hidden_state","data_type":"float","dimensions":[2,2],"description":"observation-noise covariance"},{"name":"prior_mean","var_type":"prior_vector","data_type":"float","dimensions":[2],"description":"prior mean over the initial latent state"},{"name":"prior_cov","var_type":"prior_vector","data_type":"float","dimensions":[2,2],"description":"prior covariance over the initial latent state"},{"name":"goal_mean","var_type":"hidden_state","data_type":"float","dimensions":[2],"description":"preferred state (goal)"},{"name":"control_gain","var_type":"action","data_type":"float","dimensions":[1],"description":"scalar proportional gain"},{"name":"t","var_type":"hidden_state","data_type":"integer","dimensions":[1],"description":"discrete time step"}],"connections":[{"annotation":null,"source_variables":["prior_mean"],"target_variables":["x"],"connection_type":"directed","weight":null,"description":null},{"annotation":null,"source_variables":["F"],"target_variables":["x"],"connection_type":"directed","weight":null,"description":null},{"annotation":null,"source_variables":["x"],"target_variables":["y"],"connection_type":"directed","weight":null,"description":null},{"annotation":null,"source_variables":["H"],"target_variables":["y"],"connection_type":"directed","weight":null,"description":null},{"annotation":null,"source_variables":["Q"],"target_variables":["x"],"connection_type":"directed","weight":null,"description":null},{"annotation":null,"source_variables":["R"],"target_variables":["y"],"connection_type":"directed","weight":null,"description":null},{"annotation":null,"source_variables":["u"],"target_variables":["x"],"connection_type":"directed","weight":null,"description":null},{"annotation":null,"source_variables":["goal_mean"],"target_variables":["u"],"connection_type":"directed","weight":null,"description":null},{"annotation":null,"source_variables":["control_gain"],"target_variables":["u"],"connection_type":"directed","weight":null,"description":null}],"parameters":[{"name":"F","value":[[1.0,0.0],[0.0,1.0]],"type_hint":null,"description":null},{"name":"H","value":[[1.0,0.0],[0.0,1.0]],"type_hint":null,"description":null},{"name":"Q","value":[[0.05,0.0],[0.0,0.05]],"type_hint":null,"description":null},{"name":"R","value":[[0.1,0.0],[0.0,0.1]],"type_hint":null,"description":null},{"name":"prior_mean","value":[[0.0,0.0]],"type_hint":null,"description":null},{"name":"prior_cov","value":[[0.5,0.0],[0.0,0.5]],"type_hint":null,"description":null},{"name":"goal_mean","value":[[2.0,2.0]],"type_hint":null,"description":null},{"name":"control_gain","value":[[0.3]],"type_hint":null,"description":null},{"name":"num_timesteps","value":15,"type_hint":null,"description":null},{"name":"dt","value":0.1,"type_hint":null,"description":null},{"name":"random_seed","value":42,"type_hint":null,"description":null},{"name":"num_states","value":2,"type_hint":null,"description":null},{"name":"num_observations","value":2,"type_hint":null,"description":null}],"equations":[],"time_specification":{"time_type":"Dynamic","discretization":null,"horizon":15,"step_size":null},"ontology_mappings":[{"variable_name":"F","ontology_term":"StateTransitionMatrix","description":null},{"variable_name":"H","ontology_term":"ObservationMatrix","description":null},{"variable_name":"Q","ontology_term":"ProcessNoiseCovariance","description":null},{"variable_name":"R","ontology_term":"ObservationNoiseCovariance","description":null},{"variable_name":"prior_mean","ontology_term":"PriorMean","description":null},{"variable_name":"prior_cov","ontology_term":"PriorCovariance","description":null},{"variable_name":"goal_mean","ontology_term":"PreferredState","description":null},{"variable_name":"control_gain","ontology_term":"ControlGain","description":null},{"variable_name":"x","ontology_term":"ContinuousHiddenState","description":null},{"variable_name":"y","ontology_term":"ContinuousObservation","description":null},{"variable_name":"u","ontology_term":"ControlInput","description":null},{"variable_name":"t","ontology_term":"Time","description":null}]}
