FactorGraphActiveInferenceModel-Schema DEFINITIONS AUTOMATIC TAGS ::= BEGIN

-- GNN Model Schema Definition
-- Model: Factor Graph Active Inference Model
-- A factor graph decomposition of an Active Inference generative model with:
-- - Two independent observation modalities (visual and proprioceptive)
-- - Two independent hidden state factors (position and velocity)
-- - Factored joint distribution: P(o,s) = P(o_vis|s_pos) * P(o_prop|s_vel) * P(s_pos|s_vel) * P(s_vel)
-- - Variable nodes: observation and state variables
-- - Factor nodes: likelihood and transition factors
-- - Enables modality-specific processing and efficient belief propagation

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Factor Graph Active Inference Model",
    version "1.0",
    annotation "A factor graph decomposition of an Active Inference generative model with: - Two independent observation modalities (visual and proprioceptive) - Two independent hidden state factors (position and velocity) - Factored joint distribution: P(o,s) = P(o_vis|s_pos) * P(o_prop|s_vel) * P(s_pos|s_vel) * P(s_vel) - Variable nodes: observation and state variables - Factor nodes: likelihood and transition factors - Enables modality-specific processing and efficient belief propagation",
    variables {
        {
            name "o_vis",
            varType "observation",
            dataType "integer"
            dimensions { 6, 1 }
        },
        {
            name "A_vis",
            varType "action",
            dataType "float"
            dimensions { 6, 3 }
        },
        {
            name "o_prop",
            varType "observation",
            dataType "float"
            dimensions { 4, 1 }
        }
    }
}

END -- FactorGraphActiveInferenceModel-Schema


-- MODEL_DATA: {"model_name":"Factor Graph Active Inference Model","version":"1.0","annotation":"A factor graph decomposition of an Active Inference generative model with:\n- Two independent observation modalities (visual and proprioceptive)\n- Two independent hidden state factors (position and velocity)\n- Factored joint distribution: P(o,s) = P(o_vis|s_pos) * P(o_prop|s_vel) * P(s_pos|s_vel) * P(s_vel)\n- Variable nodes: observation and state variables\n- Factor nodes: likelihood and transition factors\n- Enables modality-specific processing and efficient belief propagation","variables":[{"name":"o_vis","var_type":"observation","data_type":"integer","dimensions":[6,1],"description":"Visual observations (6 possible)"},{"name":"A_vis","var_type":"action","data_type":"float","dimensions":[6,3],"description":"Visual likelihood factor: P(o_vis | s_pos)"},{"name":"o_prop","var_type":"observation","data_type":"float","dimensions":[4,1],"description":"Proprioceptive observations (4D)"},{"name":"A_prop","var_type":"action","data_type":"float","dimensions":[4,2],"description":"Proprioceptive likelihood: P(o_prop | s_vel)"},{"name":"s_pos","var_type":"hidden_state","data_type":"float","dimensions":[3,1],"description":"Position state (3 discrete locations)"},{"name":"B_pos","var_type":"hidden_state","data_type":"float","dimensions":[3,3,2],"description":"Position transition factor"},{"name":"s_vel","var_type":"hidden_state","data_type":"float","dimensions":[2,1],"description":"Velocity state (2 levels: slow/fast)"},{"name":"B_vel","var_type":"hidden_state","data_type":"float","dimensions":[2,2,1],"description":"Velocity transition (action-independent)"},{"name":"D_pos","var_type":"hidden_state","data_type":"float","dimensions":[3],"description":"Prior over position"},{"name":"D_vel","var_type":"hidden_state","data_type":"float","dimensions":[2],"description":"Prior over velocity"},{"name":"C_vis","var_type":"hidden_state","data_type":"float","dimensions":[6],"description":"Visual preferences (goal location)"},{"name":"C_prop","var_type":"hidden_state","data_type":"float","dimensions":[4],"description":"Proprioceptive preferences (comfort)"},{"name":"\u03c0","var_type":"policy","data_type":"float","dimensions":[2],"description":"Policy (2 actions: move/stay)"},{"name":"u","var_type":"action","data_type":"integer","dimensions":[1],"description":"Selected action"},{"name":"G","var_type":"policy","data_type":"float","dimensions":[1],"description":"Expected Free Energy"},{"name":"m_pos_to_vis","var_type":"hidden_state","data_type":"float","dimensions":[3,1],"description":"Message: position\u2192visual factor"},{"name":"m_vel_to_prop","var_type":"hidden_state","data_type":"float","dimensions":[2,1],"description":"Message: velocity\u2192proprioceptive factor"},{"name":"m_vis_to_pos","var_type":"hidden_state","data_type":"float","dimensions":[3,1],"description":"Message: visual factor\u2192position"},{"name":"m_prop_to_vel","var_type":"hidden_state","data_type":"float","dimensions":[2,1],"description":"Message: proprioceptive factor\u2192velocity"},{"name":"F","var_type":"hidden_state","data_type":"float","dimensions":[1],"description":"Total Variational Free Energy (sum of factors)"},{"name":"t","var_type":"hidden_state","data_type":"integer","dimensions":[1],"description":null}],"connections":[{"source_variables":["D_pos"],"target_variables":["s_pos"],"connection_type":"directed","weight":null,"description":null},{"source_variables":["D_vel"],"target_variables":["s_vel"],"connection_type":"directed","weight":null,"description":null},{"source_variables":["s_pos"],"target_variables":["A_vis"],"connection_type":"undirected","weight":null,"description":null},{"source_variables":["A_vis"],"target_variables":["o_vis"],"connection_type":"undirected","weight":null,"description":null},{"source_variables":["s_vel"],"target_variables":["A_prop"],"connection_type":"undirected","weight":null,"description":null},{"source_variables":["A_prop"],"target_variables":["o_prop"],"connection_type":"undirected","weight":null,"description":null},{"source_variables":["s_pos"],"target_variables":["B_pos"],"connection_type":"undirected","weight":null,"description":null},{"source_variables":["s_vel"],"target_variables":["B_vel"],"connection_type":"undirected","weight":null,"description":null},{"source_variables":["B_pos"],"target_variables":["s_pos"],"connection_type":"directed","weight":null,"description":null},{"source_variables":["B_vel"],"target_variables":["s_vel"],"connection_type":"directed","weight":null,"description":null},{"source_variables":["s_pos"],"target_variables":["m_pos_to_vis"],"connection_type":"undirected","weight":null,"description":null},{"source_variables":["m_pos_to_vis"],"target_variables":["A_vis"],"connection_type":"undirected","weight":null,"description":null},{"source_variables":["o_vis"],"target_variables":["m_vis_to_pos"],"connection_type":"undirected","weight":null,"description":null},{"source_variables":["m_vis_to_pos"],"target_variables":["s_pos"],"connection_type":"undirected","weight":null,"description":null},{"source_variables":["s_vel"],"target_variables":["m_vel_to_prop"],"connection_type":"undirected","weight":null,"description":null},{"source_variables":["m_vel_to_prop"],"target_variables":["A_prop"],"connection_type":"undirected","weight":null,"description":null},{"source_variables":["o_prop"],"target_variables":["m_prop_to_vel"],"connection_type":"undirected","weight":null,"description":null},{"source_variables":["m_prop_to_vel"],"target_variables":["s_vel"],"connection_type":"undirected","weight":null,"description":null},{"source_variables":["C_vis"],"target_variables":["G"],"connection_type":"directed","weight":null,"description":null},{"source_variables":["C_prop"],"target_variables":["G"],"connection_type":"directed","weight":null,"description":null},{"source_variables":["G"],"target_variables":["\u03c0"],"connection_type":"directed","weight":null,"description":null},{"source_variables":["\u03c0"],"target_variables":["u"],"connection_type":"directed","weight":null,"description":null},{"source_variables":["B_pos"],"target_variables":["u"],"connection_type":"directed","weight":null,"description":null},{"source_variables":["s_pos"],"target_variables":["F"],"connection_type":"undirected","weight":null,"description":null},{"source_variables":["s_vel"],"target_variables":["F"],"connection_type":"undirected","weight":null,"description":null},{"source_variables":["o_vis"],"target_variables":["F"],"connection_type":"undirected","weight":null,"description":null},{"source_variables":["o_prop"],"target_variables":["F"],"connection_type":"undirected","weight":null,"description":null}],"parameters":[{"name":"A_vis","value":[[0.8,0.1,0.1],[0.1,0.8,0.1],[0.1,0.1,0.8],[0.05,0.45,0.5],[0.45,0.05,0.5],[0.5,0.5,0.0]],"type_hint":null,"description":null},{"name":"A_prop","value":[[0.9,0.1],[0.1,0.9],[0.5,0.5],[0.5,0.5]],"type_hint":null,"description":null},{"name":"B_pos","value":[[[0.9,0.1,0.0],[0.0,0.9,0.1],[0.1,0.0,0.9]],[[0.5,0.5,0.0],[0.0,0.5,0.5],[0.5,0.0,0.5]]],"type_hint":null,"description":null},{"name":"B_vel","value":[[[0.8,0.2],[0.2,0.8]]],"type_hint":null,"description":null},{"name":"D_pos","value":[[0.333,0.333,0.333]],"type_hint":null,"description":null},{"name":"D_vel","value":[[0.5,0.5]],"type_hint":null,"description":null},{"name":"C_vis","value":[[2.0,-0.5,-0.5,-0.5,-0.5,-0.5]],"type_hint":null,"description":null},{"name":"C_prop","value":[[1.0,-1.0,0.0,0.0]],"type_hint":null,"description":null},{"name":"num_positions","value":3,"type_hint":null,"description":null},{"name":"num_velocities","value":2,"type_hint":null,"description":null},{"name":"num_visual_obs","value":6,"type_hint":null,"description":null},{"name":"num_proprio_obs","value":4,"type_hint":null,"description":null},{"name":"num_actions","value":2,"type_hint":null,"description":null},{"name":"num_timesteps","value":25,"type_hint":null,"description":null},{"name":"num_modalities","value":2,"type_hint":null,"description":null},{"name":"num_state_factors","value":2,"type_hint":null,"description":null}],"equations":[],"time_specification":{"time_type":"Dynamic","discretization":null,"horizon":"Unbounded","step_size":null},"ontology_mappings":[{"variable_name":"A_vis","ontology_term":"VisualLikelihoodMatrix","description":null},{"variable_name":"A_prop","ontology_term":"ProprioceptiveLikelihoodMatrix","description":null},{"variable_name":"B_pos","ontology_term":"PositionTransitionMatrix","description":null},{"variable_name":"B_vel","ontology_term":"VelocityTransitionMatrix","description":null},{"variable_name":"D_pos","ontology_term":"PositionPrior","description":null},{"variable_name":"D_vel","ontology_term":"VelocityPrior","description":null},{"variable_name":"C_vis","ontology_term":"VisualPreferenceVector","description":null},{"variable_name":"C_prop","ontology_term":"ProprioceptivePreferenceVector","description":null},{"variable_name":"s_pos","ontology_term":"PositionHiddenState","description":null},{"variable_name":"s_vel","ontology_term":"VelocityHiddenState","description":null},{"variable_name":"o_vis","ontology_term":"VisualObservation","description":null},{"variable_name":"o_prop","ontology_term":"ProprioceptiveObservation","description":null},{"variable_name":"\u03c0","ontology_term":"PolicyVector","description":null},{"variable_name":"u","ontology_term":"Action","description":null},{"variable_name":"G","ontology_term":"ExpectedFreeEnergy","description":null},{"variable_name":"F","ontology_term":"VariationalFreeEnergy","description":null},{"variable_name":"t","ontology_term":"Time","description":null}]}
