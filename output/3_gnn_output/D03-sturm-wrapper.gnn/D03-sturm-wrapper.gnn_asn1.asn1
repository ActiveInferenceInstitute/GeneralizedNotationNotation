STURMBuilding-StockWrapperBlanket-Schema DEFINITIONS AUTOMATIC TAGS ::= BEGIN

-- GNN Model Schema Definition
-- Model: STURM Building-Stock Wrapper Blanket
-- Markov blanket for STURM as a coupled component in NEST Stage 1.
-- 
-- Boundary scope: this blanket is drawn around MODEL ↔ NEST PLATFORM. STURM
-- receives energy prices by fuel type (downscaled from the national model) and
-- returns final energy demand by fuel; renovation and stock-turnover machinery
-- (archetype shares, vintage survival, fuel switching) stays internal and is
-- never exchanged. This is the D02 mirror with sensory/active reversed on the
-- price/demand pair — D02's sensory d ↔ D03's active d, D02's active p ↔ D03's
-- sensory p. There is NO counterpart to D02's cap: D02's cap is the HIERARCHY
-- regime imposed constraint of PR #87 Q-13; STURM has no imposed constraint
-- input, so this blanket has no such sensory variable.
-- 
-- STURM assumption (labeled): STURM = MESSAGEix-Buildings (IIASA), IIASA
-- confirmation pending; residential building stock POC only (commercial
-- excluded). Catalog boundary record: catalog/models/sturm.yaml (prices in
-- USD/GJ by fuel; demand out PJ/yr; 5-year steps; ~60 regions).
-- 
-- Scope vs Q1 (Technical_Responses_Draft_v1): this file specifies the wrapper's
-- model-level I/O blanket — Q1 functions #1–#3. Q1 function #4 (the Active
-- Inference latent-summary layer, via RxInfer) is deliberately NOT modeled here;
-- those latent states are the factor-graph deliverables (D04, D07), which will
-- sit behind this blanket's internal side.
-- 
-- - Sensory states: what crosses INTO the model — energy prices by fuel type (downscaled from the national model).
-- - Active states: what crosses OUT — final energy demand by fuel (MESSAGEix-compatible). Renovation/stock-turnover rates are produced inside STURM and consumed by its own demand calculation; they are internal here, not exchanged.
-- - Internal states: archetype stock shares, renovation/turnover flows, and the turnover state machinery — never exchanged.
-- - Every exchanged variable carries the declared boundary fields (PR #80 §4 / PR #95): unit · convention · temporal support · spatial support. Prices carry the annualisation/downscaling convention of the national→STURM handoff; demand is MESSAGEix-compatible annual demand (STURM's native 5-year steps are internal; the 12 slices below are the coupling-iteration resolution, illustrative pending IIASA packaging). Spatial support follows the D05 memo (res-5 exchange via declared crosswalk).
-- - This mirrors the D02 pattern file (MESSAGEix wrapper); D03 is its price/demand mirror.
-- - Renderable form: structural blanket, no renderable form as authored — the step-11 renderer classifies it as a discrete POMDP and fails on the missing `A/B/C/D` (upstream: GeneralizedNotationNotation#111). The renderable instantiation of this blanket is the continuous-exemplar fixture block (`models/active_inference/rxinfer-bridge/fixtures/sturm/sturm_fixture.gnn.md`); until the upstream path exists, render the instantiation, not the wrapper.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "STURM Building-Stock Wrapper Blanket",
    version "1.0",
    annotation "Markov blanket for STURM as a coupled component in NEST Stage 1.  Boundary scope: this blanket is drawn around MODEL ↔ NEST PLATFORM. STURM receives energy prices by fuel type (downscaled from the national model) and returns final energy demand by fuel; renovation and stock-turnover machinery (archetype shares, vintage survival, fuel switching) stays internal and is never exchanged. This is the D02 mirror with sensory/active reversed on the price/demand pair — D02's sensory d ↔ D03's active d, D02's active p ↔ D03's sensory p. There is NO counterpart to D02's cap: D02's cap is the HIERARCHY regime imposed constraint of PR #87 Q-13; STURM has no imposed constraint input, so this blanket has no such sensory variable.  STURM assumption (labeled): STURM = MESSAGEix-Buildings (IIASA), IIASA confirmation pending; residential building stock POC only (commercial excluded). Catalog boundary record: catalog/models/sturm.yaml (prices in USD/GJ by fuel; demand out PJ/yr; 5-year steps; ~60 regions).  Scope vs Q1 (Technical_Responses_Draft_v1): this file specifies the wrapper's model-level I/O blanket — Q1 functions #1–#3. Q1 function #4 (the Active Inference latent-summary layer, via RxInfer) is deliberately NOT modeled here; those latent states are the factor-graph deliverables (D04, D07), which will sit behind this blanket's internal side.  - Sensory states: what crosses INTO the model — energy prices by fuel type (downscaled from the national model). - Active states: what crosses OUT — final energy demand by fuel (MESSAGEix-compatible). Renovation/stock-turnover rates are produced inside STURM and consumed by its own demand calculation; they are internal here, not exchanged. - Internal states: archetype stock shares, renovation/turnover flows, and the turnover state machinery — never exchanged. - Every exchanged variable carries the declared boundary fields (PR #80 §4 / PR #95): unit · convention · temporal support · spatial support. Prices carry the annualisation/downscaling convention of the national→STURM handoff; demand is MESSAGEix-compatible annual demand (STURM's native 5-year steps are internal; the 12 slices below are the coupling-iteration resolution, illustrative pending IIASA packaging). Spatial support follows the D05 memo (res-5 exchange via declared crosswalk). - This mirrors the D02 pattern file (MESSAGEix wrapper); D03 is its price/demand mirror. - Renderable form: structural blanket, no renderable form as authored — the step-11 renderer classifies it as a discrete POMDP and fails on the missing `A/B/C/D` (upstream: GeneralizedNotationNotation#111). The renderable instantiation of this blanket is the continuous-exemplar fixture block (`models/active_inference/rxinfer-bridge/fixtures/sturm/sturm_fixture.gnn.md`); until the upstream path exists, render the instantiation, not the wrapper.",
    variables {
        {
            name "p",
            varType "hidden_state",
            dataType "float"
            dimensions { 2, 12 }
        },
        {
            name "d",
            varType "hidden_state",
            dataType "float"
            dimensions { 2, 12 }
        },
        {
            name "q",
            varType "hidden_state",
            dataType "float"
            dimensions { 4 }
        }
    }
}

END -- STURMBuilding-StockWrapperBlanket-Schema


-- MODEL_DATA: {"model_name":"STURM Building-Stock Wrapper Blanket","version":"1.0","annotation":"Markov blanket for STURM as a coupled component in NEST Stage 1.\n\nBoundary scope: this blanket is drawn around MODEL \u2194 NEST PLATFORM. STURM\nreceives energy prices by fuel type (downscaled from the national model) and\nreturns final energy demand by fuel; renovation and stock-turnover machinery\n(archetype shares, vintage survival, fuel switching) stays internal and is\nnever exchanged. This is the D02 mirror with sensory/active reversed on the\nprice/demand pair \u2014 D02's sensory d \u2194 D03's active d, D02's active p \u2194 D03's\nsensory p. There is NO counterpart to D02's cap: D02's cap is the HIERARCHY\nregime imposed constraint of PR #87 Q-13; STURM has no imposed constraint\ninput, so this blanket has no such sensory variable.\n\nSTURM assumption (labeled): STURM = MESSAGEix-Buildings (IIASA), IIASA\nconfirmation pending; residential building stock POC only (commercial\nexcluded). Catalog boundary record: catalog/models/sturm.yaml (prices in\nUSD/GJ by fuel; demand out PJ/yr; 5-year steps; ~60 regions).\n\nScope vs Q1 (Technical_Responses_Draft_v1): this file specifies the wrapper's\nmodel-level I/O blanket \u2014 Q1 functions #1\u2013#3. Q1 function #4 (the Active\nInference latent-summary layer, via RxInfer) is deliberately NOT modeled here;\nthose latent states are the factor-graph deliverables (D04, D07), which will\nsit behind this blanket's internal side.\n\n- Sensory states: what crosses INTO the model \u2014 energy prices by fuel type (downscaled from the national model).\n- Active states: what crosses OUT \u2014 final energy demand by fuel (MESSAGEix-compatible). Renovation/stock-turnover rates are produced inside STURM and consumed by its own demand calculation; they are internal here, not exchanged.\n- Internal states: archetype stock shares, renovation/turnover flows, and the turnover state machinery \u2014 never exchanged.\n- Every exchanged variable carries the declared boundary fields (PR #80 \u00a74 / PR #95): unit \u00b7 convention \u00b7 temporal support \u00b7 spatial support. Prices carry the annualisation/downscaling convention of the national\u2192STURM handoff; demand is MESSAGEix-compatible annual demand (STURM's native 5-year steps are internal; the 12 slices below are the coupling-iteration resolution, illustrative pending IIASA packaging). Spatial support follows the D05 memo (res-5 exchange via declared crosswalk).\n- This mirrors the D02 pattern file (MESSAGEix wrapper); D03 is its price/demand mirror.\n- Renderable form: structural blanket, no renderable form as authored \u2014 the step-11 renderer classifies it as a discrete POMDP and fails on the missing `A/B/C/D` (upstream: GeneralizedNotationNotation#111). The renderable instantiation of this blanket is the continuous-exemplar fixture block (`models/active_inference/rxinfer-bridge/fixtures/sturm/sturm_fixture.gnn.md`); until the upstream path exists, render the instantiation, not the wrapper.","variables":[{"name":"p","var_type":"hidden_state","data_type":"float","dimensions":[2,12],"description":"energy prices by fuel type [USD/GJ; annualisation/downscaling convention; temporal support: 12 slices \u2014 illustrative, pending IIASA packaging]"},{"name":"d","var_type":"hidden_state","data_type":"float","dimensions":[2,12],"description":"final energy demand by fuel [PJ/yr; MESSAGEix-compatible]"},{"name":"q","var_type":"hidden_state","data_type":"float","dimensions":[4],"description":"archetype stock shares [share; sums to 1]"},{"name":"r","var_type":"hidden_state","data_type":"float","dimensions":[4,12],"description":"renovation / turnover flows per archetype per slice [share/yr]"},{"name":"u","var_type":"action","data_type":"float","dimensions":[8,1],"description":"internal turnover state summary (vintage survival, fuel-switching machinery)"},{"name":"t","var_type":"hidden_state","data_type":"integer","dimensions":[1],"description":"coupling iteration index"}],"connections":[{"source_variables":["p"],"target_variables":["u"],"connection_type":"directed","weight":null,"description":null},{"source_variables":["u"],"target_variables":["q"],"connection_type":"directed","weight":null,"description":null},{"source_variables":["u"],"target_variables":["r"],"connection_type":"directed","weight":null,"description":null},{"source_variables":["q"],"target_variables":["d"],"connection_type":"directed","weight":null,"description":null},{"source_variables":["r"],"target_variables":["d"],"connection_type":"directed","weight":null,"description":null},{"source_variables":["d"],"target_variables":["p"],"connection_type":"directed","weight":null,"description":null}],"parameters":[{"name":"p","value":[[0.0,0.0]],"type_hint":null,"description":null},{"name":"num_fuel_types","value":2,"type_hint":null,"description":null},{"name":"num_time_slices","value":12,"type_hint":null,"description":null},{"name":"num_archetypes","value":4,"type_hint":null,"description":null},{"name":"num_regions","value":1,"type_hint":null,"description":null}],"equations":[],"time_specification":{"time_type":"Dynamic","discretization":"DiscreteTime","horizon":"Unbounded","step_size":null},"ontology_mappings":[{"variable_name":"p","ontology_term":"Observation","description":null},{"variable_name":"d","ontology_term":"Action","description":null},{"variable_name":"q","ontology_term":"HiddenState","description":null},{"variable_name":"r","ontology_term":"HiddenState","description":null},{"variable_name":"u","ontology_term":"HiddenState","description":null},{"variable_name":"t","ontology_term":"Time","description":null}]}
