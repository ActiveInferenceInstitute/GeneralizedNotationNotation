SimpleMDPAgent-Schema DEFINITIONS AUTOMATIC TAGS ::= BEGIN

-- GNN Model Schema Definition
-- Model: Simple MDP Agent
-- This model describes a fully observable Markov Decision Process (MDP):
-- 
-- - 4 hidden states representing grid positions (corners of a 2x2 grid).
-- - Observations are identical to states (A = identity matrix).
-- - 4 actions: stay, move-north, move-south, move-east.
-- - Preferences strongly favor state/observation 3 (goal location).
-- - Tests the degenerate POMDP case where partial observability is absent.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Simple MDP Agent",
    version "1.0",
    annotation "This model describes a fully observable Markov Decision Process (MDP):  - 4 hidden states representing grid positions (corners of a 2x2 grid). - Observations are identical to states (A = identity matrix). - 4 actions: stay, move-north, move-south, move-east. - Preferences strongly favor state/observation 3 (goal location). - Tests the degenerate POMDP case where partial observability is absent.",
    variables {
        {
            name "A",
            varType "likelihood_matrix",
            dataType "float"
            dimensions { 4, 4 }
        },
        {
            name "B",
            varType "transition_matrix",
            dataType "float"
            dimensions { 4, 4, 4 }
        },
        {
            name "C",
            varType "preference_vector",
            dataType "float"
            dimensions { 4 }
        }
    }
}

END -- SimpleMDPAgent-Schema


-- MODEL_DATA: {"model_name":"Simple MDP Agent","version":"1.0","annotation":"This model describes a fully observable Markov Decision Process (MDP):\n\n- 4 hidden states representing grid positions (corners of a 2x2 grid).\n- Observations are identical to states (A = identity matrix).\n- 4 actions: stay, move-north, move-south, move-east.\n- Preferences strongly favor state/observation 3 (goal location).\n- Tests the degenerate POMDP case where partial observability is absent.","variables":[{"name":"A","var_type":"likelihood_matrix","data_type":"float","dimensions":[4,4],"description":"Observation model: identity (fully observable)"},{"name":"B","var_type":"transition_matrix","data_type":"float","dimensions":[4,4,4],"description":"State transitions given state and action"},{"name":"C","var_type":"preference_vector","data_type":"float","dimensions":[4],"description":"Log-preferences over observations"},{"name":"D","var_type":"prior_vector","data_type":"float","dimensions":[4],"description":"Prior over initial hidden states"},{"name":"s","var_type":"hidden_state","data_type":"float","dimensions":[4,1],"description":"Current hidden state distribution"},{"name":"s_prime","var_type":"hidden_state","data_type":"float","dimensions":[4,1],"description":"Next hidden state distribution"},{"name":"o","var_type":"observation","data_type":"integer","dimensions":[4,1],"description":"Current observation (same as state in MDP)"},{"name":"\u03c0","var_type":"policy","data_type":"float","dimensions":[4],"description":"Policy (distribution over actions)"},{"name":"u","var_type":"action","data_type":"integer","dimensions":[1],"description":"Action taken"},{"name":"G","var_type":"policy","data_type":"float","dimensions":[1],"description":"Expected Free Energy (per policy)"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["s"],"target_variables":["s_prime"],"connection_type":"directed","weight":null,"description":null},{"annotation":null,"source_variables":["A"],"target_variables":["o"],"connection_type":"undirected","weight":null,"description":null},{"annotation":null,"source_variables":["s"],"target_variables":["B"],"connection_type":"undirected","weight":null,"description":null},{"annotation":null,"source_variables":["C"],"target_variables":["G"],"connection_type":"directed","weight":null,"description":null},{"annotation":null,"source_variables":["G"],"target_variables":["\u03c0"],"connection_type":"directed","weight":null,"description":null},{"annotation":null,"source_variables":["\u03c0"],"target_variables":["u"],"connection_type":"directed","weight":null,"description":null},{"annotation":null,"source_variables":["B"],"target_variables":["u"],"connection_type":"directed","weight":null,"description":null},{"annotation":null,"source_variables":["u"],"target_variables":["s_prime"],"connection_type":"directed","weight":null,"description":null}],"parameters":[{"name":"A","value":[[1.0,0.0,0.0,0.0],[0.0,1.0,0.0,0.0],[0.0,0.0,1.0,0.0],[0.0,0.0,0.0,1.0]],"type_hint":null,"description":null},{"name":"B","value":[[[0.9,0.1,0.0,0.0],[0.1,0.9,0.0,0.0],[0.0,0.0,0.9,0.1],[0.0,0.0,0.1,0.9]],[[0.1,0.9,0.0,0.0],[0.9,0.1,0.0,0.0],[0.0,0.0,0.1,0.9],[0.0,0.0,0.9,0.1]],[[0.0,0.0,0.9,0.1],[0.0,0.0,0.1,0.9],[0.9,0.1,0.0,0.0],[0.1,0.9,0.0,0.0]],[[0.0,0.0,0.1,0.9],[0.0,0.0,0.9,0.1],[0.1,0.9,0.0,0.0],[0.9,0.1,0.0,0.0]]],"type_hint":null,"description":null},{"name":"C","value":[[0.0,0.0,0.0,3.0]],"type_hint":null,"description":null},{"name":"D","value":[[0.25,0.25,0.25,0.25]],"type_hint":null,"description":null},{"name":"num_hidden_states","value":4,"type_hint":null,"description":null},{"name":"num_obs","value":4,"type_hint":null,"description":null},{"name":"num_actions","value":4,"type_hint":null,"description":null},{"name":"num_timesteps","value":25,"type_hint":null,"description":null}],"equations":[],"time_specification":{"time_type":"Dynamic","discretization":null,"horizon":"Unbounded","step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"t","ontology_term":"Time","description":null}]}
