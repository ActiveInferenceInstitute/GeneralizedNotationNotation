StochasticContinuousDynamicsAgent-Schema DEFINITIONS AUTOMATIC TAGS ::= BEGIN

-- GNN Model Schema Definition
-- Model: Stochastic Continuous Dynamics Agent
-- A continuous-state Active Inference agent whose dynamics include
-- explicit process and observation noise. This sample exercises the
-- continuous-time path of the language: Time=Continuous, state as a
-- multi-dimensional vector, and Equations containing noise terms ε_state
-- and ε_obs that downstream renderers must handle.
-- 
-- - 4-dimensional continuous hidden state (e.g., position + velocity in 2D)
-- - 2-dimensional continuous observation (noisy position readout)
-- - Linear Gaussian dynamics: ẋ = Fx + Gu + ε_state
-- - Linear Gaussian observation: o = Hx + ε_obs
-- - Precision parameters γ_state (process) and γ_obs (observation)
-- 
-- Used to validate that downstream backends either generate SDE solvers
-- (Stan via latent-variable sampling, NumPyro) or raise a clean
-- "unsupported feature" warning (PyMDP, which is discrete-only).

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Stochastic Continuous Dynamics Agent",
    version "1.0",
    annotation "A continuous-state Active Inference agent whose dynamics include explicit process and observation noise. This sample exercises the continuous-time path of the language: Time=Continuous, state as a multi-dimensional vector, and Equations containing noise terms ε_state and ε_obs that downstream renderers must handle.  - 4-dimensional continuous hidden state (e.g., position + velocity in 2D) - 2-dimensional continuous observation (noisy position readout) - Linear Gaussian dynamics: ẋ = Fx + Gu + ε_state - Linear Gaussian observation: o = Hx + ε_obs - Precision parameters γ_state (process) and γ_obs (observation)  Used to validate that downstream backends either generate SDE solvers (Stan via latent-variable sampling, NumPyro) or raise a clean ""unsupported feature"" warning (PyMDP, which is discrete-only).",
    variables {
        {
            name "x",
            varType "hidden_state",
            dataType "float"
            dimensions { 4, 1 }
        },
        {
            name "o",
            varType "observation",
            dataType "float"
            dimensions { 2, 1 }
        },
        {
            name "u",
            varType "action",
            dataType "float"
            dimensions { 2, 1 }
        }
    }
}

END -- StochasticContinuousDynamicsAgent-Schema


-- MODEL_DATA: {"model_name":"Stochastic Continuous Dynamics Agent","version":"1.0","annotation":"A continuous-state Active Inference agent whose dynamics include\nexplicit process and observation noise. This sample exercises the\ncontinuous-time path of the language: Time=Continuous, state as a\nmulti-dimensional vector, and Equations containing noise terms \u03b5_state\nand \u03b5_obs that downstream renderers must handle.\n\n- 4-dimensional continuous hidden state (e.g., position + velocity in 2D)\n- 2-dimensional continuous observation (noisy position readout)\n- Linear Gaussian dynamics: \u1e8b = Fx + Gu + \u03b5_state\n- Linear Gaussian observation: o = Hx + \u03b5_obs\n- Precision parameters \u03b3_state (process) and \u03b3_obs (observation)\n\nUsed to validate that downstream backends either generate SDE solvers\n(Stan via latent-variable sampling, NumPyro) or raise a clean\n\"unsupported feature\" warning (PyMDP, which is discrete-only).","variables":[{"name":"x","var_type":"hidden_state","data_type":"float","dimensions":[4,1],"description":"Continuous hidden state vector"},{"name":"o","var_type":"observation","data_type":"float","dimensions":[2,1],"description":"Continuous observation vector"},{"name":"u","var_type":"action","data_type":"float","dimensions":[2,1],"description":"Continuous control input"},{"name":"F","var_type":"hidden_state","data_type":"float","dimensions":[4,4],"description":"State transition matrix (drift)"},{"name":"G","var_type":"policy","data_type":"float","dimensions":[4,2],"description":"Control gain matrix"},{"name":"H","var_type":"hidden_state","data_type":"float","dimensions":[2,4],"description":"Observation matrix"},{"name":"gamma_state","var_type":"hidden_state","data_type":"float","dimensions":[1],"description":"Process noise precision"},{"name":"gamma_obs","var_type":"observation","data_type":"float","dimensions":[1],"description":"Observation noise precision"},{"name":"epsilon_state","var_type":"hidden_state","data_type":"float","dimensions":[4,1],"description":"Process noise \u03b5 ~ N(0, \u03b3_state^-1 * I)"},{"name":"epsilon_obs","var_type":"observation","data_type":"float","dimensions":[2,1],"description":"Observation noise \u03b5 ~ N(0, \u03b3_obs^-1 * I)"}],"connections":[{"source_variables":["x","u","epsilon_state"],"target_variables":["F"],"connection_type":"directed","weight":null,"description":null},{"source_variables":["F"],"target_variables":["x"],"connection_type":"directed","weight":null,"description":null},{"source_variables":["x","epsilon_obs"],"target_variables":["H"],"connection_type":"directed","weight":null,"description":null},{"source_variables":["H"],"target_variables":["o"],"connection_type":"directed","weight":null,"description":null},{"source_variables":["gamma_state"],"target_variables":["epsilon_state"],"connection_type":"undirected","weight":null,"description":null},{"source_variables":["gamma_obs"],"target_variables":["epsilon_obs"],"connection_type":"undirected","weight":null,"description":null}],"parameters":[{"name":"F","value":[[1.0,0.0,0.1,0.0],[0.0,1.0,0.0,0.1],[0.0,0.0,0.95,0.0],[0.0,0.0,0.0,0.95]],"type_hint":null,"description":null},{"name":"G","value":[[0.0,0.0],[0.0,0.0],[1.0,0.0],[0.0,1.0]],"type_hint":null,"description":null},{"name":"H","value":[[1.0,0.0,0.0,0.0],[0.0,1.0,0.0,0.0]],"type_hint":null,"description":null},{"name":"gamma_state","value":[[10.0]],"type_hint":null,"description":null},{"name":"gamma_obs","value":[[5.0]],"type_hint":null,"description":null},{"name":"state_dim","value":4,"type_hint":null,"description":null},{"name":"obs_dim","value":2,"type_hint":null,"description":null},{"name":"control_dim","value":2,"type_hint":null,"description":null},{"name":"num_timesteps","value":50,"type_hint":null,"description":null},{"name":"time_horizon","value":5.0,"type_hint":null,"description":null},{"name":"integration_step","value":0.1,"type_hint":null,"description":null}],"equations":[],"time_specification":{"time_type":"Static","discretization":"ContinuousTime","horizon":"5.0","step_size":null},"ontology_mappings":[{"variable_name":"x","ontology_term":"ContinuousHiddenState","description":null},{"variable_name":"o","ontology_term":"ContinuousObservation","description":null},{"variable_name":"u","ontology_term":"ContinuousAction","description":null},{"variable_name":"F","ontology_term":"DriftMatrix","description":null},{"variable_name":"G","ontology_term":"ControlMatrix","description":null},{"variable_name":"H","ontology_term":"ObservationMatrix","description":null},{"variable_name":"gamma_state","ontology_term":"ProcessNoisePrecision","description":null},{"variable_name":"gamma_obs","ontology_term":"ObservationNoisePrecision","description":null},{"variable_name":"epsilon_state","ontology_term":"ProcessNoise","description":null},{"variable_name":"epsilon_obs","ontology_term":"ObservationNoise","description":null}]}
