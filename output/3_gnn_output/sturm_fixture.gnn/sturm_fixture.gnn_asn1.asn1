NESTD03Synthetic2-StateLGSSM-Schema DEFINITIONS AUTOMATIC TAGS ::= BEGIN

-- GNN Model Schema Definition
-- Model: NEST D03 Synthetic 2-State LGSSM
-- Passive linear-Gaussian state-space model (no control input) generating the
-- summary indices of the D03 STURM wrapper blanket over T coupling iterations.
-- - Hidden state x = (renovation_rate_dev, price_pressure), dimensionless deviations.
-- - Observation y = (price_index, demand_index, stock_index, turnover_index): relative indices of fuel prices p
--   (sensory, into STURM), final energy demand d (active, out of STURM), the
--   archetype stock aggregate and the turnover aggregate against fixed reference
--   values (see the fixture JSON, `blanket.references`).
-- - q_agg/r_agg are internal aggregates carried in the fixture for posterior
--   checks only; they never cross the blanket.
-- - There is NO counterpart to D02's cap: the cap is the Q-13 HIERARCHY imposed
--   constraint of the MESSAGEix side; STURM receives none.
-- Deliverable D03 (AII); mirror of the D04 fixture under the D03 blanket.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "NEST D03 Synthetic 2-State LGSSM",
    version "1.0",
    annotation "Passive linear-Gaussian state-space model (no control input) generating the summary indices of the D03 STURM wrapper blanket over T coupling iterations. - Hidden state x = (renovation_rate_dev, price_pressure), dimensionless deviations. - Observation y = (price_index, demand_index, stock_index, turnover_index): relative indices of fuel prices p   (sensory, into STURM), final energy demand d (active, out of STURM), the   archetype stock aggregate and the turnover aggregate against fixed reference   values (see the fixture JSON, `blanket.references`). - q_agg/r_agg are internal aggregates carried in the fixture for posterior   checks only; they never cross the blanket. - There is NO counterpart to D02's cap: the cap is the Q-13 HIERARCHY imposed   constraint of the MESSAGEix side; STURM receives none. Deliverable D03 (AII); mirror of the D04 fixture under the D03 blanket.",
    variables {
        {
            name "x",
            varType "hidden_state",
            dataType "float"
            dimensions { 2, 1 }
        },
        {
            name "y",
            varType "hidden_state",
            dataType "float"
            dimensions { 4, 1 }
        },
        {
            name "F",
            varType "hidden_state",
            dataType "float"
            dimensions { 2, 2 }
        }
    }
}

END -- NESTD03Synthetic2-StateLGSSM-Schema


-- MODEL_DATA: {"model_name":"NEST D03 Synthetic 2-State LGSSM","version":"1.0","annotation":"Passive linear-Gaussian state-space model (no control input) generating the\nsummary indices of the D03 STURM wrapper blanket over T coupling iterations.\n- Hidden state x = (renovation_rate_dev, price_pressure), dimensionless deviations.\n- Observation y = (price_index, demand_index, stock_index, turnover_index): relative indices of fuel prices p\n  (sensory, into STURM), final energy demand d (active, out of STURM), the\n  archetype stock aggregate and the turnover aggregate against fixed reference\n  values (see the fixture JSON, `blanket.references`).\n- q_agg/r_agg are internal aggregates carried in the fixture for posterior\n  checks only; they never cross the blanket.\n- There is NO counterpart to D02's cap: the cap is the Q-13 HIERARCHY imposed\n  constraint of the MESSAGEix side; STURM receives none.\nDeliverable D03 (AII); mirror of the D04 fixture under the D03 blanket.","variables":[{"name":"x","var_type":"hidden_state","data_type":"float","dimensions":[2,1],"description":"hidden state (renovation_rate_dev, price_pressure)"},{"name":"y","var_type":"hidden_state","data_type":"float","dimensions":[4,1],"description":"exchanged-array summary indices"},{"name":"F","var_type":"hidden_state","data_type":"float","dimensions":[2,2],"description":"state transition"},{"name":"H","var_type":"hidden_state","data_type":"float","dimensions":[4,2],"description":"observation matrix"},{"name":"Q","var_type":"hidden_state","data_type":"float","dimensions":[2,2],"description":"process-noise covariance"},{"name":"R","var_type":"hidden_state","data_type":"float","dimensions":[4,4],"description":"observation-noise covariance"},{"name":"prior_mean","var_type":"prior_vector","data_type":"float","dimensions":[2],"description":"prior mean over x_1"},{"name":"prior_cov","var_type":"prior_vector","data_type":"float","dimensions":[2,2],"description":"prior covariance over x_1"},{"name":"t","var_type":"hidden_state","data_type":"integer","dimensions":[1],"description":"coupling iteration"}],"connections":[{"source_variables":["prior_mean"],"target_variables":["x"],"connection_type":"directed","weight":null,"description":null},{"source_variables":["F"],"target_variables":["x"],"connection_type":"directed","weight":null,"description":null},{"source_variables":["x"],"target_variables":["y"],"connection_type":"directed","weight":null,"description":null},{"source_variables":["H"],"target_variables":["y"],"connection_type":"directed","weight":null,"description":null},{"source_variables":["Q"],"target_variables":["x"],"connection_type":"directed","weight":null,"description":null},{"source_variables":["R"],"target_variables":["y"],"connection_type":"directed","weight":null,"description":null}],"parameters":[{"name":"F","value":[[0.8,-0.15],[0.05,0.9]],"type_hint":null,"description":null},{"name":"H","value":[[-0.4,0.7],[0.5,-0.3],[0.6,0.0],[0.8,0.0]],"type_hint":null,"description":null},{"name":"Q","value":[[0.0036,-0.0003],[-0.0003,0.0049]],"type_hint":null,"description":null},{"name":"R","value":[[0.0016,0.0,0.0,0.0],[0.0,0.0025,0.0,0.0],[0.0,0.0,0.0009,0.0],[0.0,0.0,0.0,0.0012]],"type_hint":null,"description":null},{"name":"prior_mean","value":[[0.02,0.0]],"type_hint":null,"description":null},{"name":"prior_cov","value":[[0.02,0.0],[0.0,0.02]],"type_hint":null,"description":null},{"name":"num_timesteps","value":24,"type_hint":null,"description":null},{"name":"random_seed","value":20260911,"type_hint":null,"description":null},{"name":"num_states","value":2,"type_hint":null,"description":null},{"name":"num_observations","value":4,"type_hint":null,"description":null},{"name":"num_regions","value":1,"type_hint":null,"description":null},{"name":"num_fuel_types","value":2,"type_hint":null,"description":null},{"name":"num_time_slices","value":12,"type_hint":null,"description":null},{"name":"num_archetypes","value":4,"type_hint":null,"description":null}],"equations":[],"time_specification":{"time_type":"Dynamic","discretization":null,"horizon":24,"step_size":null},"ontology_mappings":[{"variable_name":"F","ontology_term":"StateTransitionMatrix","description":null},{"variable_name":"H","ontology_term":"ObservationMatrix","description":null},{"variable_name":"Q","ontology_term":"ProcessNoiseCovariance","description":null},{"variable_name":"R","ontology_term":"ObservationNoiseCovariance","description":null},{"variable_name":"prior_mean","ontology_term":"PriorMean","description":null},{"variable_name":"prior_cov","ontology_term":"PriorCovariance","description":null},{"variable_name":"x","ontology_term":"ContinuousHiddenState","description":null},{"variable_name":"y","ontology_term":"ContinuousObservation","description":null},{"variable_name":"t","ontology_term":"Time","description":null}]}
