Three-LevelTemporalHierarchyAgent-Schema DEFINITIONS AUTOMATIC TAGS ::= BEGIN

-- GNN Model Schema Definition
-- Model: Three-Level Temporal Hierarchy Agent
-- A three-level hierarchical Active Inference agent with distinct temporal scales:
-- 
-- - Level 0 (fast, 100ms): Sensorimotor control — immediate reflexive responses
-- - Level 1 (medium, 1s): Tactical planning — goal-directed behavior sequences
-- - Level 2 (slow, 10s): Strategic planning — long-term objective management
-- - Top-down flow: Strategy sets tactical goals, tactics set sensorimotor preferences
-- - Bottom-up flow: Sensorimotor observations inform tactical beliefs, tactical outcomes inform strategy
-- - Each level maintains its own generative model with A, B, C, D matrices
-- - Timescale separation encoded via update ratios (Level 2 updates every 10 Level 0 steps)
-- - Demonstrates deep temporal models from Friston et al. hierarchical Active Inference

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Three-Level Temporal Hierarchy Agent",
    version "1.0",
    annotation "A three-level hierarchical Active Inference agent with distinct temporal scales:  - Level 0 (fast, 100ms): Sensorimotor control — immediate reflexive responses - Level 1 (medium, 1s): Tactical planning — goal-directed behavior sequences - Level 2 (slow, 10s): Strategic planning — long-term objective management - Top-down flow: Strategy sets tactical goals, tactics set sensorimotor preferences - Bottom-up flow: Sensorimotor observations inform tactical beliefs, tactical outcomes inform strategy - Each level maintains its own generative model with A, B, C, D matrices - Timescale separation encoded via update ratios (Level 2 updates every 10 Level 0 steps) - Demonstrates deep temporal models from Friston et al. hierarchical Active Inference",
    variables {
        {
            name "A_level0",
            varType "action",
            dataType "float"
            dimensions { 3, 4 }
        },
        {
            name "B_level0",
            varType "hidden_state",
            dataType "float"
            dimensions { 4, 4, 3 }
        },
        {
            name "C_level0",
            varType "hidden_state",
            dataType "float"
            dimensions { 3 }
        }
    }
}

END -- Three-LevelTemporalHierarchyAgent-Schema


-- MODEL_DATA: {"model_name":"Three-Level Temporal Hierarchy Agent","version":"1.0","annotation":"A three-level hierarchical Active Inference agent with distinct temporal scales:\n\n- Level 0 (fast, 100ms): Sensorimotor control \u2014 immediate reflexive responses\n- Level 1 (medium, 1s): Tactical planning \u2014 goal-directed behavior sequences\n- Level 2 (slow, 10s): Strategic planning \u2014 long-term objective management\n- Top-down flow: Strategy sets tactical goals, tactics set sensorimotor preferences\n- Bottom-up flow: Sensorimotor observations inform tactical beliefs, tactical outcomes inform strategy\n- Each level maintains its own generative model with A, B, C, D matrices\n- Timescale separation encoded via update ratios (Level 2 updates every 10 Level 0 steps)\n- Demonstrates deep temporal models from Friston et al. hierarchical Active Inference","variables":[{"name":"A_level0","var_type":"action","data_type":"float","dimensions":[3,4],"description":"Level 0 likelihood: P(fast_obs | fast_state)"},{"name":"B_level0","var_type":"hidden_state","data_type":"float","dimensions":[4,4,3],"description":"Level 0 transitions: P(fast_state' | fast_state, fast_action)"},{"name":"C_level0","var_type":"hidden_state","data_type":"float","dimensions":[3],"description":"Level 0 preferences (modulated by Level 1)"},{"name":"D_level0","var_type":"hidden_state","data_type":"float","dimensions":[4],"description":"Level 0 prior over initial states"},{"name":"s_level0","var_type":"hidden_state","data_type":"float","dimensions":[4,1],"description":"Level 0 hidden state belief"},{"name":"o_level0","var_type":"observation","data_type":"integer","dimensions":[3,1],"description":"Level 0 observation"},{"name":"pi0","var_type":"policy","data_type":"float","dimensions":[3],"description":"Level 0 policy"},{"name":"u_level0","var_type":"action","data_type":"integer","dimensions":[1],"description":"Level 0 action"},{"name":"G0","var_type":"hidden_state","data_type":"float","dimensions":[1],"description":"Level 0 Expected Free Energy"},{"name":"A_level1","var_type":"action","data_type":"float","dimensions":[4,3],"description":"Level 1 likelihood: P(tactic_obs | tactic_state)"},{"name":"B_level1","var_type":"hidden_state","data_type":"float","dimensions":[3,3,3],"description":"Level 1 transitions"},{"name":"C_level1","var_type":"hidden_state","data_type":"float","dimensions":[4],"description":"Level 1 preferences (modulated by Level 2)"},{"name":"D_level1","var_type":"hidden_state","data_type":"float","dimensions":[3],"description":"Level 1 prior (modulated by Level 2 predictions)"},{"name":"s_level1","var_type":"hidden_state","data_type":"float","dimensions":[3,1],"description":"Level 1 hidden state belief"},{"name":"o_level1","var_type":"observation","data_type":"float","dimensions":[4,1],"description":"Level 1 observation (= summary of Level 0 state trajectory)"},{"name":"pi1","var_type":"policy","data_type":"float","dimensions":[3],"description":"Level 1 policy"},{"name":"u_level1","var_type":"action","data_type":"integer","dimensions":[1],"description":"Level 1 action"},{"name":"G1","var_type":"hidden_state","data_type":"float","dimensions":[1],"description":"Level 1 Expected Free Energy"},{"name":"A_level2","var_type":"action","data_type":"float","dimensions":[3,2],"description":"Level 2 likelihood: P(strategy_obs | strategy_state)"},{"name":"B_level2","var_type":"hidden_state","data_type":"float","dimensions":[2,2,2],"description":"Level 2 transitions"},{"name":"C_level2","var_type":"hidden_state","data_type":"float","dimensions":[3],"description":"Level 2 preferences (fixed strategic goals)"},{"name":"D_level2","var_type":"hidden_state","data_type":"float","dimensions":[2],"description":"Level 2 prior over strategies"},{"name":"s_level2","var_type":"hidden_state","data_type":"float","dimensions":[2,1],"description":"Level 2 hidden state belief"},{"name":"o_level2","var_type":"observation","data_type":"float","dimensions":[3,1],"description":"Level 2 observation (= summary of Level 1 outcomes)"},{"name":"pi2","var_type":"policy","data_type":"float","dimensions":[2],"description":"Level 2 policy"},{"name":"u_level2","var_type":"action","data_type":"integer","dimensions":[1],"description":"Level 2 action"},{"name":"G2","var_type":"hidden_state","data_type":"float","dimensions":[1],"description":"Level 2 Expected Free Energy"},{"name":"tau_level0","var_type":"hidden_state","data_type":"float","dimensions":[1],"description":"Level 0 time constant (0.1s)"},{"name":"tau_level1","var_type":"hidden_state","data_type":"float","dimensions":[1],"description":"Level 1 time constant (1.0s)"},{"name":"tau_level2","var_type":"hidden_state","data_type":"float","dimensions":[1],"description":"Level 2 time constant (10.0s)"},{"name":"t","var_type":"hidden_state","data_type":"integer","dimensions":[1],"description":"Global discrete time counter"}],"connections":[{"annotation":null,"source_variables":["D_level0"],"target_variables":["s_level0"],"connection_type":"directed","weight":null,"description":null},{"annotation":null,"source_variables":["s_level0"],"target_variables":["A_level0"],"connection_type":"undirected","weight":null,"description":null},{"annotation":null,"source_variables":["A_level0"],"target_variables":["o_level0"],"connection_type":"undirected","weight":null,"description":null},{"annotation":null,"source_variables":["C_level0"],"target_variables":["G0"],"connection_type":"directed","weight":null,"description":null},{"annotation":null,"source_variables":["G0"],"target_variables":["pi0"],"connection_type":"directed","weight":null,"description":null},{"annotation":null,"source_variables":["pi0"],"target_variables":["u_level0"],"connection_type":"directed","weight":null,"description":null},{"annotation":null,"source_variables":["B_level0"],"target_variables":["u_level0"],"connection_type":"directed","weight":null,"description":null},{"annotation":null,"source_variables":["D_level1"],"target_variables":["s_level1"],"connection_type":"directed","weight":null,"description":null},{"annotation":null,"source_variables":["s_level1"],"target_variables":["A_level1"],"connection_type":"undirected","weight":null,"description":null},{"annotation":null,"source_variables":["A_level1"],"target_variables":["o_level1"],"connection_type":"undirected","weight":null,"description":null},{"annotation":null,"source_variables":["C_level1"],"target_variables":["G1"],"connection_type":"directed","weight":null,"description":null},{"annotation":null,"source_variables":["G1"],"target_variables":["pi1"],"connection_type":"directed","weight":null,"description":null},{"annotation":null,"source_variables":["pi1"],"target_variables":["u_level1"],"connection_type":"directed","weight":null,"description":null},{"annotation":null,"source_variables":["B_level1"],"target_variables":["u_level1"],"connection_type":"directed","weight":null,"description":null},{"annotation":null,"source_variables":["D_level2"],"target_variables":["s_level2"],"connection_type":"directed","weight":null,"description":null},{"annotation":null,"source_variables":["s_level2"],"target_variables":["A_level2"],"connection_type":"undirected","weight":null,"description":null},{"annotation":null,"source_variables":["A_level2"],"target_variables":["o_level2"],"connection_type":"undirected","weight":null,"description":null},{"annotation":null,"source_variables":["C_level2"],"target_variables":["G2"],"connection_type":"directed","weight":null,"description":null},{"annotation":null,"source_variables":["G2"],"target_variables":["pi2"],"connection_type":"directed","weight":null,"description":null},{"annotation":null,"source_variables":["pi2"],"target_variables":["u_level2"],"connection_type":"directed","weight":null,"description":null},{"annotation":null,"source_variables":["B_level2"],"target_variables":["u_level2"],"connection_type":"directed","weight":null,"description":null},{"annotation":null,"source_variables":["s_level2"],"target_variables":["C_level1"],"connection_type":"directed","weight":null,"description":null},{"annotation":null,"source_variables":["s_level1"],"target_variables":["C_level0"],"connection_type":"directed","weight":null,"description":null},{"annotation":null,"source_variables":["s_level2"],"target_variables":["D_level1"],"connection_type":"directed","weight":null,"description":null},{"annotation":null,"source_variables":["s_level0"],"target_variables":["o_level1"],"connection_type":"directed","weight":null,"description":null},{"annotation":null,"source_variables":["s_level1"],"target_variables":["o_level2"],"connection_type":"directed","weight":null,"description":null}],"parameters":[{"name":"A_level0","value":[[0.85,0.05,0.05,0.05],[0.05,0.85,0.05,0.05],[0.05,0.05,0.85,0.05]],"type_hint":null,"description":null},{"name":"C_level0","value":[[0.0,-1.0,1.0]],"type_hint":null,"description":null},{"name":"D_level0","value":[[0.25,0.25,0.25,0.25]],"type_hint":null,"description":null},{"name":"A_level1","value":[[0.8,0.1,0.1],[0.1,0.8,0.1],[0.1,0.1,0.8],[0.1,0.1,0.1]],"type_hint":null,"description":null},{"name":"C_level1","value":[[-0.5,1.0,1.5,-1.0]],"type_hint":null,"description":null},{"name":"D_level1","value":[[0.33,0.33,0.34]],"type_hint":null,"description":null},{"name":"A_level2","value":[[0.9,0.1],[0.1,0.9],[0.1,0.1]],"type_hint":null,"description":null},{"name":"C_level2","value":[[-1.0,2.0,0.5]],"type_hint":null,"description":null},{"name":"D_level2","value":[[0.5,0.5]],"type_hint":null,"description":null},{"name":"tau_level0","value":[[0.1]],"type_hint":null,"description":null},{"name":"tau_level1","value":[[1.0]],"type_hint":null,"description":null},{"name":"tau_level2","value":[[10.0]],"type_hint":null,"description":null},{"name":"B_level0","value":[[[0.9,0.05,0.05,0.0],[0.05,0.9,0.05,0.0],[0.05,0.05,0.9,0.0],[0.0,0.0,0.0,1.0]],[[0.05,0.9,0.05,0.0],[0.9,0.05,0.05,0.0],[0.05,0.05,0.9,0.0],[0.0,0.0,0.0,1.0]],[[0.9,0.05,0.05,0.0],[0.05,0.9,0.05,0.0],[0.05,0.05,0.9,0.0],[0.0,0.0,0.0,1.0]]],"type_hint":null,"description":null},{"name":"B_level1","value":[[[0.9,0.05,0.05],[0.05,0.9,0.05],[0.05,0.05,0.9]],[[0.05,0.9,0.05],[0.9,0.05,0.05],[0.05,0.05,0.9]],[[0.9,0.05,0.05],[0.05,0.9,0.05],[0.05,0.05,0.9]]],"type_hint":null,"description":null},{"name":"B_level2","value":[[[0.95,0.05],[0.05,0.95]]],"type_hint":null,"description":null},{"name":"num_hidden_states","value":24,"type_hint":null,"description":null},{"name":"num_obs","value":36,"type_hint":null,"description":null},{"name":"num_actions","value":3,"type_hint":null,"description":null},{"name":"num_levels","value":3,"type_hint":null,"description":null},{"name":"num_states_l0","value":4,"type_hint":null,"description":null},{"name":"num_obs_l0","value":3,"type_hint":null,"description":null},{"name":"num_actions_l0","value":3,"type_hint":null,"description":null},{"name":"num_states_l1","value":3,"type_hint":null,"description":null},{"name":"num_obs_l1","value":4,"type_hint":null,"description":null},{"name":"num_actions_l1","value":3,"type_hint":null,"description":null},{"name":"num_states_l2","value":2,"type_hint":null,"description":null},{"name":"num_obs_l2","value":3,"type_hint":null,"description":null},{"name":"num_actions_l2","value":2,"type_hint":null,"description":null},{"name":"timescale_ratio_1_0","value":10,"type_hint":null,"description":null},{"name":"timescale_ratio_2_1","value":10,"type_hint":null,"description":null},{"name":"num_timesteps","value":100,"type_hint":null,"description":null}],"equations":[],"time_specification":{"time_type":"Dynamic","discretization":null,"horizon":100,"step_size":null},"ontology_mappings":[{"variable_name":"A_level0","ontology_term":"FastLikelihoodMatrix","description":null},{"variable_name":"B_level0","ontology_term":"FastTransitionMatrix","description":null},{"variable_name":"C_level0","ontology_term":"FastPreferenceVector","description":null},{"variable_name":"D_level0","ontology_term":"FastPrior","description":null},{"variable_name":"s_level0","ontology_term":"FastHiddenState","description":null},{"variable_name":"o_level0","ontology_term":"FastObservation","description":null},{"variable_name":"pi0","ontology_term":"FastPolicyVector","description":null},{"variable_name":"u_level0","ontology_term":"FastAction","description":null},{"variable_name":"G0","ontology_term":"FastExpectedFreeEnergy","description":null},{"variable_name":"A_level1","ontology_term":"TacticalLikelihoodMatrix","description":null},{"variable_name":"B_level1","ontology_term":"TacticalTransitionMatrix","description":null},{"variable_name":"C_level1","ontology_term":"TacticalPreferenceVector","description":null},{"variable_name":"D_level1","ontology_term":"TacticalPrior","description":null},{"variable_name":"s_level1","ontology_term":"TacticalHiddenState","description":null},{"variable_name":"o_level1","ontology_term":"TacticalObservation","description":null},{"variable_name":"pi1","ontology_term":"TacticalPolicyVector","description":null},{"variable_name":"u_level1","ontology_term":"TacticalAction","description":null},{"variable_name":"G1","ontology_term":"TacticalExpectedFreeEnergy","description":null},{"variable_name":"A_level2","ontology_term":"StrategicLikelihoodMatrix","description":null},{"variable_name":"B_level2","ontology_term":"StrategicTransitionMatrix","description":null},{"variable_name":"C_level2","ontology_term":"StrategicPreferenceVector","description":null},{"variable_name":"D_level2","ontology_term":"StrategicPrior","description":null},{"variable_name":"s_level2","ontology_term":"StrategicHiddenState","description":null},{"variable_name":"o_level2","ontology_term":"StrategicObservation","description":null},{"variable_name":"pi2","ontology_term":"StrategicPolicyVector","description":null},{"variable_name":"u_level2","ontology_term":"StrategicAction","description":null},{"variable_name":"G2","ontology_term":"StrategicExpectedFreeEnergy","description":null},{"variable_name":"tau_level0","ontology_term":"FastTimeConstant","description":null},{"variable_name":"tau_level1","ontology_term":"TacticalTimeConstant","description":null},{"variable_name":"tau_level2","ontology_term":"StrategicTimeConstant","description":null},{"variable_name":"t","ontology_term":"Time","description":null}]}
