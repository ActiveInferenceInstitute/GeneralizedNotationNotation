DynamicPerceptionModel-Schema DEFINITIONS AUTOMATIC TAGS ::= BEGIN

-- GNN Model Schema Definition
-- Model: Dynamic Perception Model
-- A dynamic perception model extending the static model with temporal dynamics:
-- 
-- - 2 hidden states evolving over discrete time via transition matrix B
-- - 2 observations generated from states via recognition matrix A
-- - Prior D constrains the initial hidden state
-- - No action selection — the agent passively observes a changing world
-- - Demonstrates belief updating (state inference) across time steps
-- - Suitable for tracking hidden sources from noisy observations

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "Dynamic Perception Model",
    version "1.0",
    annotation "A dynamic perception model extending the static model with temporal dynamics:  - 2 hidden states evolving over discrete time via transition matrix B - 2 observations generated from states via recognition matrix A - Prior D constrains the initial hidden state - No action selection — the agent passively observes a changing world - Demonstrates belief updating (state inference) across time steps - Suitable for tracking hidden sources from noisy observations",
    variables {
        {
            name "A",
            varType "likelihood_matrix",
            dataType "float"
            dimensions { 2, 2 }
        },
        {
            name "B",
            varType "transition_matrix",
            dataType "float"
            dimensions { 2, 2 }
        },
        {
            name "D",
            varType "prior_vector",
            dataType "float"
            dimensions { 2, 1 }
        }
    }
}

END -- DynamicPerceptionModel-Schema


-- MODEL_DATA: {"model_name":"Dynamic Perception Model","version":"1.0","annotation":"A dynamic perception model extending the static model with temporal dynamics:\n\n- 2 hidden states evolving over discrete time via transition matrix B\n- 2 observations generated from states via recognition matrix A\n- Prior D constrains the initial hidden state\n- No action selection \u2014 the agent passively observes a changing world\n- Demonstrates belief updating (state inference) across time steps\n- Suitable for tracking hidden sources from noisy observations","variables":[{"name":"A","var_type":"likelihood_matrix","data_type":"float","dimensions":[2,2],"description":"Recognition matrix: P(observation | hidden state)"},{"name":"B","var_type":"transition_matrix","data_type":"float","dimensions":[2,2],"description":"Transition matrix: P(s_{t+1} | s_t) \u2014 no action dependence"},{"name":"D","var_type":"prior_vector","data_type":"float","dimensions":[2,1],"description":"Prior over initial hidden states"},{"name":"s_t","var_type":"hidden_state","data_type":"float","dimensions":[2,1],"description":"Hidden state belief at time t"},{"name":"s_prime","var_type":"hidden_state","data_type":"float","dimensions":[2,1],"description":"Hidden state belief at time t+1"},{"name":"o_t","var_type":"observation","data_type":"integer","dimensions":[2,1],"description":"Observation at time t"},{"name":"F","var_type":"hidden_state","data_type":"float","dimensions":[1],"description":"Variational Free Energy (negative ELBO)"},{"name":"t","var_type":"hidden_state","data_type":"integer","dimensions":[1],"description":"Discrete time index"}],"connections":[{"annotation":null,"source_variables":["D"],"target_variables":["s_t"],"connection_type":"directed","weight":null,"description":null},{"annotation":null,"source_variables":["s_t"],"target_variables":["A"],"connection_type":"undirected","weight":null,"description":null},{"annotation":null,"source_variables":["A"],"target_variables":["o_t"],"connection_type":"undirected","weight":null,"description":null},{"annotation":null,"source_variables":["s_t"],"target_variables":["B"],"connection_type":"undirected","weight":null,"description":null},{"annotation":null,"source_variables":["B"],"target_variables":["s_prime"],"connection_type":"directed","weight":null,"description":null},{"annotation":null,"source_variables":["s_t"],"target_variables":["F"],"connection_type":"undirected","weight":null,"description":null},{"annotation":null,"source_variables":["o_t"],"target_variables":["F"],"connection_type":"undirected","weight":null,"description":null}],"parameters":[{"name":"A","value":[[0.9,0.1],[0.2,0.8]],"type_hint":null,"description":null},{"name":"B","value":[[0.7,0.3],[0.3,0.7]],"type_hint":null,"description":null},{"name":"D","value":[[0.5,0.5]],"type_hint":null,"description":null},{"name":"num_hidden_states","value":2,"type_hint":null,"description":null},{"name":"num_obs","value":2,"type_hint":null,"description":null},{"name":"num_timesteps","value":10,"type_hint":null,"description":null}],"equations":[],"time_specification":{"time_type":"Dynamic","discretization":null,"horizon":10,"step_size":null},"ontology_mappings":[{"variable_name":"A","ontology_term":"RecognitionMatrix","description":null},{"variable_name":"B","ontology_term":"TransitionMatrix","description":null},{"variable_name":"D","ontology_term":"Prior","description":null},{"variable_name":"s_t","ontology_term":"HiddenState","description":null},{"variable_name":"s_prime","ontology_term":"NextHiddenState","description":null},{"variable_name":"o_t","ontology_term":"Observation","description":null},{"variable_name":"F","ontology_term":"VariationalFreeEnergy","description":null},{"variable_name":"t","ontology_term":"Time","description":null}]}
