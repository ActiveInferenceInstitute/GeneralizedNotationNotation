POMDPGridWorld3x3-Schema DEFINITIONS AUTOMATIC TAGS ::= BEGIN

-- GNN Model Schema Definition
-- Model: POMDP GridWorld 3x3
-- Discrete 3x3 GridWorld POMDP for strict cross-framework validation. The model has one hidden state factor with 9 grid cells, one observation modality with noisy cell observations, and one control factor with 5 boundary-clamped actions: up, down, left, right, and stay.

GNNModel ::= SEQUENCE {
    modelName       UTF8String,
    version         UTF8String,
    annotation      UTF8String OPTIONAL,
    variables       SEQUENCE OF Variable OPTIONAL,
    connections     SEQUENCE OF Connection OPTIONAL,
    parameters      SEQUENCE OF Parameter OPTIONAL
}

Variable ::= SEQUENCE {
    name            UTF8String,
    varType         UTF8String,
    dataType        UTF8String,
    dimensions      SEQUENCE OF INTEGER OPTIONAL,
    description     UTF8String OPTIONAL
}

Connection ::= SEQUENCE {
    sourceVariables SEQUENCE OF UTF8String,
    targetVariables SEQUENCE OF UTF8String,
    connectionType  UTF8String,
    weight          REAL OPTIONAL,
    description     UTF8String OPTIONAL
}

Parameter ::= SEQUENCE {
    name            UTF8String,
    value           UTF8String,
    typeHint        UTF8String OPTIONAL,
    description     UTF8String OPTIONAL
}

-- Example Values
exampleModel GNNModel ::= {
    modelName "POMDP GridWorld 3x3",
    version "1.0",
    annotation "Discrete 3x3 GridWorld POMDP for strict cross-framework validation. The model has one hidden state factor with 9 grid cells, one observation modality with noisy cell observations, and one control factor with 5 boundary-clamped actions: up, down, left, right, and stay.",
    variables {
        {
            name "A",
            varType "likelihood_matrix",
            dataType "float"
            dimensions { 9, 9 }
        },
        {
            name "B",
            varType "transition_matrix",
            dataType "float"
            dimensions { 9, 9, 5 }
        },
        {
            name "C",
            varType "preference_vector",
            dataType "float"
            dimensions { 9 }
        }
    }
}

END -- POMDPGridWorld3x3-Schema


-- MODEL_DATA: {"model_name":"POMDP GridWorld 3x3","version":"1.0","annotation":"Discrete 3x3 GridWorld POMDP for strict cross-framework validation. The model has one hidden state factor with 9 grid cells, one observation modality with noisy cell observations, and one control factor with 5 boundary-clamped actions: up, down, left, right, and stay.","variables":[{"name":"A","var_type":"likelihood_matrix","data_type":"float","dimensions":[9,9],"description":"Likelihood matrix: observations by hidden states"},{"name":"B","var_type":"transition_matrix","data_type":"float","dimensions":[9,9,5],"description":"Transition tensor: next_state, previous_state, action"},{"name":"C","var_type":"preference_vector","data_type":"float","dimensions":[9],"description":"Log-preferences over observations"},{"name":"D","var_type":"prior_vector","data_type":"float","dimensions":[9],"description":"Prior over initial hidden state"},{"name":"E","var_type":"policy","data_type":"float","dimensions":[5],"description":"Policy prior over actions"},{"name":"s","var_type":"hidden_state","data_type":"float","dimensions":[9,1],"description":"Current hidden state distribution"},{"name":"s_prime","var_type":"hidden_state","data_type":"float","dimensions":[9,1],"description":"Next hidden state distribution"},{"name":"o","var_type":"observation","data_type":"integer","dimensions":[9,1],"description":"Current observation"},{"name":"\u03c0","var_type":"policy","data_type":"float","dimensions":[5],"description":"Policy distribution over actions"},{"name":"u","var_type":"action","data_type":"integer","dimensions":[1],"description":"Action index"},{"name":"G","var_type":"policy","data_type":"float","dimensions":[1],"description":"Expected Free Energy per action"},{"name":"t","var_type":"hidden_state","data_type":"integer","dimensions":[1],"description":"Discrete time step"}],"connections":[{"annotation":null,"source_variables":["D"],"target_variables":["s"],"connection_type":"directed","weight":null,"description":null},{"annotation":null,"source_variables":["s"],"target_variables":["A"],"connection_type":"undirected","weight":null,"description":null},{"annotation":null,"source_variables":["A"],"target_variables":["o"],"connection_type":"undirected","weight":null,"description":null},{"annotation":null,"source_variables":["s"],"target_variables":["B"],"connection_type":"undirected","weight":null,"description":null},{"annotation":null,"source_variables":["B"],"target_variables":["u"],"connection_type":"directed","weight":null,"description":null},{"annotation":null,"source_variables":["u"],"target_variables":["s_prime"],"connection_type":"directed","weight":null,"description":null},{"annotation":null,"source_variables":["C"],"target_variables":["G"],"connection_type":"directed","weight":null,"description":null},{"annotation":null,"source_variables":["E"],"target_variables":["\u03c0"],"connection_type":"directed","weight":null,"description":null},{"annotation":null,"source_variables":["G"],"target_variables":["\u03c0"],"connection_type":"directed","weight":null,"description":null},{"annotation":null,"source_variables":["\u03c0"],"target_variables":["u"],"connection_type":"directed","weight":null,"description":null},{"annotation":null,"source_variables":["s"],"target_variables":["s_prime"],"connection_type":"directed","weight":null,"description":null}],"parameters":[{"name":"A","value":[[0.85,0.01875,0.01875,0.01875,0.01875,0.01875,0.01875,0.01875,0.01875],[0.01875,0.85,0.01875,0.01875,0.01875,0.01875,0.01875,0.01875,0.01875],[0.01875,0.01875,0.85,0.01875,0.01875,0.01875,0.01875,0.01875,0.01875],[0.01875,0.01875,0.01875,0.85,0.01875,0.01875,0.01875,0.01875,0.01875],[0.01875,0.01875,0.01875,0.01875,0.85,0.01875,0.01875,0.01875,0.01875],[0.01875,0.01875,0.01875,0.01875,0.01875,0.85,0.01875,0.01875,0.01875],[0.01875,0.01875,0.01875,0.01875,0.01875,0.01875,0.85,0.01875,0.01875],[0.01875,0.01875,0.01875,0.01875,0.01875,0.01875,0.01875,0.85,0.01875],[0.01875,0.01875,0.01875,0.01875,0.01875,0.01875,0.01875,0.01875,0.85]],"type_hint":null,"description":null},{"name":"B","value":[[[1.0,0.0,1.0,0.0,1.0],[0.0,0.0,1.0,0.0,0.0],[0.0,0.0,0.0,0.0,0.0],[1.0,0.0,0.0,0.0,0.0],[0.0,0.0,0.0,0.0,0.0],[0.0,0.0,0.0,0.0,0.0],[0.0,0.0,0.0,0.0,0.0],[0.0,0.0,0.0,0.0,0.0],[0.0,0.0,0.0,0.0,0.0]],[[0.0,0.0,0.0,1.0,0.0],[1.0,0.0,0.0,0.0,1.0],[0.0,0.0,1.0,0.0,0.0],[0.0,0.0,0.0,0.0,0.0],[1.0,0.0,0.0,0.0,0.0],[0.0,0.0,0.0,0.0,0.0],[0.0,0.0,0.0,0.0,0.0],[0.0,0.0,0.0,0.0,0.0],[0.0,0.0,0.0,0.0,0.0]],[[0.0,0.0,0.0,0.0,0.0],[0.0,0.0,0.0,1.0,0.0],[1.0,0.0,0.0,1.0,1.0],[0.0,0.0,0.0,0.0,0.0],[0.0,0.0,0.0,0.0,0.0],[1.0,0.0,0.0,0.0,0.0],[0.0,0.0,0.0,0.0,0.0],[0.0,0.0,0.0,0.0,0.0],[0.0,0.0,0.0,0.0,0.0]],[[0.0,1.0,0.0,0.0,0.0],[0.0,0.0,0.0,0.0,0.0],[0.0,0.0,0.0,0.0,0.0],[0.0,0.0,1.0,0.0,1.0],[0.0,0.0,1.0,0.0,0.0],[0.0,0.0,0.0,0.0,0.0],[1.0,0.0,0.0,0.0,0.0],[0.0,0.0,0.0,0.0,0.0],[0.0,0.0,0.0,0.0,0.0]],[[0.0,0.0,0.0,0.0,0.0],[0.0,1.0,0.0,0.0,0.0],[0.0,0.0,0.0,0.0,0.0],[0.0,0.0,0.0,1.0,0.0],[0.0,0.0,0.0,0.0,1.0],[0.0,0.0,1.0,0.0,0.0],[0.0,0.0,0.0,0.0,0.0],[1.0,0.0,0.0,0.0,0.0],[0.0,0.0,0.0,0.0,0.0]],[[0.0,0.0,0.0,0.0,0.0],[0.0,0.0,0.0,0.0,0.0],[0.0,1.0,0.0,0.0,0.0],[0.0,0.0,0.0,0.0,0.0],[0.0,0.0,0.0,1.0,0.0],[0.0,0.0,0.0,1.0,1.0],[0.0,0.0,0.0,0.0,0.0],[0.0,0.0,0.0,0.0,0.0],[1.0,0.0,0.0,0.0,0.0]],[[0.0,0.0,0.0,0.0,0.0],[0.0,0.0,0.0,0.0,0.0],[0.0,0.0,0.0,0.0,0.0],[0.0,1.0,0.0,0.0,0.0],[0.0,0.0,0.0,0.0,0.0],[0.0,0.0,0.0,0.0,0.0],[0.0,1.0,1.0,0.0,1.0],[0.0,0.0,1.0,0.0,0.0],[0.0,0.0,0.0,0.0,0.0]],[[0.0,0.0,0.0,0.0,0.0],[0.0,0.0,0.0,0.0,0.0],[0.0,0.0,0.0,0.0,0.0],[0.0,0.0,0.0,0.0,0.0],[0.0,1.0,0.0,0.0,0.0],[0.0,0.0,0.0,0.0,0.0],[0.0,0.0,0.0,1.0,0.0],[0.0,1.0,0.0,0.0,1.0],[0.0,0.0,1.0,0.0,0.0]],[[0.0,0.0,0.0,0.0,0.0],[0.0,0.0,0.0,0.0,0.0],[0.0,0.0,0.0,0.0,0.0],[0.0,0.0,0.0,0.0,0.0],[0.0,0.0,0.0,0.0,0.0],[0.0,1.0,0.0,0.0,0.0],[0.0,0.0,0.0,0.0,0.0],[0.0,0.0,0.0,1.0,0.0],[0.0,1.0,0.0,1.0,1.0]]],"type_hint":null,"description":null},{"name":"C","value":[[0.0,0.1,0.3,0.1,0.4,0.8,0.3,0.8,3.0]],"type_hint":null,"description":null},{"name":"D","value":[[1.0,0.0,0.0,0.0,0.0,0.0,0.0,0.0,0.0]],"type_hint":null,"description":null},{"name":"E","value":[[0.2,0.2,0.2,0.2,0.2]],"type_hint":null,"description":null},{"name":"num_hidden_states","value":9,"type_hint":null,"description":null},{"name":"num_obs","value":9,"type_hint":null,"description":null},{"name":"num_actions","value":5,"type_hint":null,"description":null},{"name":"num_timesteps","value":15,"type_hint":null,"description":null},{"name":"random_seed","value":42,"type_hint":null,"description":null},{"name":"b_tensor_order","value":"next_state_previous_state_action","type_hint":null,"description":null},{"name":"grid_rows","value":3,"type_hint":null,"description":null},{"name":"grid_cols","value":3,"type_hint":null,"description":null},{"name":"goal_state","value":8,"type_hint":null,"description":null},{"name":"action_labels","value":"up,down,left,right,stay","type_hint":null,"description":null}],"equations":[{"label":null,"content":"State inference uses the observation likelihood and previous predictive belief. Action selection minimizes expected free energy under the shared transition tensor.","format":"latex","description":null}],"time_specification":{"time_type":"Dynamic","discretization":null,"horizon":15,"step_size":null},"ontology_mappings":[{"variable_name":"A","ontology_term":"LikelihoodMatrix","description":null},{"variable_name":"B","ontology_term":"TransitionMatrix","description":null},{"variable_name":"C","ontology_term":"LogPreferenceVector","description":null},{"variable_name":"D","ontology_term":"PriorOverHiddenStates","description":null},{"variable_name":"E","ontology_term":"Habit","description":null},{"variable_name":"G","ontology_term":"ExpectedFreeEnergy","description":null},{"variable_name":"s","ontology_term":"HiddenState","description":null},{"variable_name":"s_prime","ontology_term":"NextHiddenState","description":null},{"variable_name":"o","ontology_term":"Observation","description":null},{"variable_name":"\u03c0","ontology_term":"PolicyVector","description":null},{"variable_name":"u","ontology_term":"Action","description":null},{"variable_name":"t","ontology_term":"Time","description":null}]}
